CDS-PJTR-CP2208R-NOTIFY DEFINITIONS ::= BEGIN

IMPORTS
    cp2208R
        FROM CDS-PJTR-CP2208R
    NOTIFICATION-GROUP, OBJECT-GROUP
        FROM SNMPv2-CONF
    MODULE-IDENTITY, NOTIFICATION-TYPE, OBJECT-TYPE
        FROM SNMPv2-SMI
    DisplayString
        FROM SNMPv2-TC
    ;

cdcp2208RNotification MODULE-IDENTITY
    LAST-UPDATED  "201212191650Z" -- December 19, 2012
    ORGANIZATION
        "Christie Digital Systems, Inc."
    CONTACT-INFO
        "Christie Digital Systems
         Customer Service

         Postal:  10550 Camden Drive
         Cypress, Ca 90630
         USA

         Tel:  +1 800 221-8025

         E-mail:  support@cds.com"
    DESCRIPTION
        "The MIB module for CDS cinema projector notifications. Alarms
         correspond to those generated within the TPC  and are
         documented in the manual."
    REVISION      "201212191650Z" -- December 19, 2012
    DESCRIPTION
        "Replaced LampLifeRotation with the LampHalfLife notification."

    ::= { cp2208R 100 }

cdcp2208RNotificationGroups OBJECT IDENTIFIER ::= { cdcp2208RNotification 1 }

-- ====================================================================
-- 
-- Object groups

cdcp2208RNotificationObjectsGroup OBJECT-GROUP
    OBJECTS
        { cdSensorName, cdSensorValue, cdComponentName, cdLampHours,
        cdTamperName, cdTamperValue }
    STATUS        current
    DESCRIPTION
        "Notification objects"
    ::= { cdcp2208RNotificationGroups 1 }

-- cdcp2208RNotificationGroup OBJECT-GROUP OBJECTS

cdcp2208RNotificationGroup NOTIFICATION-GROUP
    NOTIFICATIONS
        { cdcp2208RNotifyFan, cdcp2208RNotifyInterlock,
        cdcp2208RNotifyTemperature, cdcp2208RNotifySystemComm,
        cdcp2208RNotifyLampStrike,
        cdcp2208RNotifyLampUnexpectedOff, cdcp2208RNotifySecurityTamper,
        cdcp2208RNotifyCoolant }
    STATUS        current
    DESCRIPTION
        "Notifications"
    ::= { cdcp2208RNotificationGroups 2 }

cdcp2208RNotificationObjects OBJECT IDENTIFIER ::= { cdcp2208RNotification 2 }

-- ====================================================================
-- 
-- Notification objects

cdSensorName OBJECT-TYPE
    SYNTAX        DisplayString
    MAX-ACCESS    accessible-for-notify
    STATUS        current
    DESCRIPTION
        "Identifies the specific sensor which triggered the
         notification."
    ::= { cdcp2208RNotificationObjects 1 }

cdSensorValue OBJECT-TYPE
    SYNTAX        DisplayString
    MAX-ACCESS    accessible-for-notify
    STATUS        current
    DESCRIPTION
        "A string with the formatted value of the sensor which
         triggered the notification."
    ::= { cdcp2208RNotificationObjects 2 }

cdComponentName OBJECT-TYPE
    SYNTAX        DisplayString
    MAX-ACCESS    accessible-for-notify
    STATUS        current
    DESCRIPTION
        "Descripes the component which caused a comm error to trigger
         the notification."
    ::= { cdcp2208RNotificationObjects 3 }

cdLampHours OBJECT-TYPE
    SYNTAX        INTEGER (0..65535)
    MAX-ACCESS    accessible-for-notify
    STATUS        current
    DESCRIPTION
        "Hours the installed lamp has operated."
    ::= { cdcp2208RNotificationObjects 4 }

cdTamperName OBJECT-TYPE
    SYNTAX        DisplayString
    MAX-ACCESS    accessible-for-notify
    STATUS        current
    DESCRIPTION
        "Identifies the specific tamper which triggered the
         notification."
    ::= { cdcp2208RNotificationObjects 5 }

cdTamperValue OBJECT-TYPE
    SYNTAX        DisplayString
    MAX-ACCESS    accessible-for-notify
    STATUS        current
    DESCRIPTION
        "A string with the formatted value of the tamper which
         triggered the notification."
    ::= { cdcp2208RNotificationObjects 6 }

cdcp2208RNotifications OBJECT IDENTIFIER ::= { cdcp2208RNotification 3 }

cdcp2208RNotificationsPrefix OBJECT IDENTIFIER ::= { cdcp2208RNotifications 0 }

-- ====================================================================
-- 
-- Projector notifications

cdcp2208RNotifyFan NOTIFICATION-TYPE
    OBJECTS
        { cdSensorName, cdSensorValue }
    STATUS        current
    DESCRIPTION
        "A fan speed error has occured."
    ::= { cdcp2208RNotificationsPrefix 1 }

cdcp2208RNotifyInterlock NOTIFICATION-TYPE
    OBJECTS
        { cdSensorName, cdSensorValue }
    STATUS        current
    DESCRIPTION
        "An interlock was tripped."
    ::= { cdcp2208RNotificationsPrefix 2 }

cdcp2208RNotifyTemperature NOTIFICATION-TYPE
    OBJECTS
        { cdSensorName, cdSensorValue }
    STATUS        current
    DESCRIPTION
        "Temperature sensor breached operational threshold."
    ::= { cdcp2208RNotificationsPrefix 3 }

cdcp2208RNotifySystemComm NOTIFICATION-TYPE
    OBJECTS
        { cdComponentName }
    STATUS        current
    DESCRIPTION
        "Communications to critical system component failed."
    ::= { cdcp2208RNotificationsPrefix 4 }

cdcp2208RNotifyLampStrike NOTIFICATION-TYPE
    OBJECTS
        { cdLampHours }
    STATUS        current
    DESCRIPTION
        "Lamp failed to strike."
    ::= { cdcp2208RNotificationsPrefix 6 }

cdcp2208RNotifyLampUnexpectedOff NOTIFICATION-TYPE
    OBJECTS
        { cdLampHours }
    STATUS        current
    DESCRIPTION
        "Unexpected lamp failure."
    ::= { cdcp2208RNotificationsPrefix 7 }

cdcp2208RNotifyCoolant NOTIFICATION-TYPE
    STATUS        current
    DESCRIPTION
        "Liquid cooling pump failure"
    ::= { cdcp2208RNotificationsPrefix 8 }

cdcp2208RNotifySecurityTamper NOTIFICATION-TYPE
    OBJECTS
        { cdTamperName, cdTamperValue }
    STATUS        current
    DESCRIPTION
        "Security System has been tampered tamper name and tamper
         state."
    ::= { cdcp2208RNotificationsPrefix 10 }

END
