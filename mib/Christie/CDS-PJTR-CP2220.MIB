CDS-PJTR-CP2220 DEFINITIONS ::= BEGIN

IMPORTS
    cdEsProjector
        FROM CDS-SMI
    Gauge32, Integer32, MODULE-IDENTITY, OBJECT-IDENTITY, OBJECT-TYPE
        FROM SNMPv2-SMI
    DisplayString, TEXTUAL-CONVENTION, TruthValue
        FROM SNMPv2-TC
    ;

cp2220 MODULE-IDENTITY
    LAST-UPDATED  "201008031914Z" -- August 03, 2010
    ORGANIZATION
        "Christie Digital Systems, Inc."
    CONTACT-INFO
        "Christie Digital Systems
         Customer Service

         Postal:     10550 Camden Drive
         Cypress, Ca 90630
         USA

         Tel:        +1 800 221-8025

         E-mail:     support@christiedigital.com"
    DESCRIPTION
        "The MIB module for CDS Entertainment Solutions CP2220 Cinema
         projector.
         iso(1).org(3).dod(6).internet(1).private(4).enterprises(1)
         .christiedigital(25766)
         .christieDigitalProduct(1)
         .cdEs(12).cdEsProjector(1)"
    REVISION      "201009141437Z" -- September 14, 2010
    DESCRIPTION
        "Added support for ICP Disk space"
    REVISION      "201008031933Z" -- August 03, 2010
    DESCRIPTION
        "Added: Icp1v2, Icp1v8, Icp2v5, Icp3v3,
         IcpCommunicating,LdCommunicating, LdLink0, LdLink1, LdLink2,
         LdLink3"
    REVISION      "201008031917Z" -- August 03, 2010
    DESCRIPTION
        "Added: LvpsACok, LvpsDCok,PowerGoodVid,
         PowerGood1v2and2v5,PowerGood1v8and3v3,
         PowerGood24vEXT,PowerGood24vSTBY"
    REVISION      "201008031915Z" -- August 03, 2010
    DESCRIPTION
        "Added: IcpType, DmdType, SatelliteTypes, IlsInstalled,TpcType,
         TpcOS,TpcDiskSpaceAvailable,TpcDiskSpaceUsed,
         TpcMemoryAvailable"
    REVISION      "200911251644Z" -- November 25, 2009
    DESCRIPTION
        "Changed name board to LD"
    REVISION      "200910131641Z" -- October 13, 2009
    DESCRIPTION
        "Fixed issue with MIB compile, part of history table was not
         deleted when transfered to common mib"
     REVISION      "201103301915Z" -- March 30, 2011
     DESCRIPTION
	 "Updated: IcpType to include ICP 1.5 - 16 MegaByte Flash"

    ::= { cdEsProjector 2 }

-- ====================================================================
-- 
-- Lens Table - a table of lens entries

Cdcp2220LensIndex ::= TEXTUAL-CONVENTION
    STATUS        current
    DESCRIPTION
        "A value used to index the Lens table."
    SYNTAX        Integer32

-- ====================================================================
-- 
-- Versions - a table of serial numbers of install sw/hw components

Cdcp2220SerialNumberIdx ::= TEXTUAL-CONVENTION
    STATUS        current
    DESCRIPTION
        "A value used to index projector serial numbers."
    SYNTAX        Integer32 (1..64)

-- ====================================================================
-- 
-- Versions - a table of versions of install sw/hw components

Cdcp2220VersionsIdx ::= TEXTUAL-CONVENTION
    STATUS        current
    DESCRIPTION
        "A value used to index projector versions."
    SYNTAX        Integer32 (1..64)

-- ====================================================================
-- 
-- Admin only

X509Certificate ::= TEXTUAL-CONVENTION
    STATUS        current
    DESCRIPTION
        "An X509 digital certificate encoded as an ASN.1 DER object."
    SYNTAX        OCTET STRING (SIZE(0..4096))

cdcp2220Config OBJECT IDENTIFIER ::= { cp2220 1 }

cdcp2220VersionsTable OBJECT-TYPE
    SYNTAX        SEQUENCE OF Cdcp2220VersionsEntry
    MAX-ACCESS    not-accessible
    STATUS        current
    DESCRIPTION
        "A table listing the versions of the projectors hardware and
         software components."
    ::= { cdcp2220Config 1 }

cdcp2220VersionsEntry OBJECT-TYPE
    SYNTAX        Cdcp2220VersionsEntry
    MAX-ACCESS    not-accessible
    STATUS        current
    DESCRIPTION
        "The projector component description and version."
    INDEX
        { cdcp2220VersionsIndex }
    ::= { cdcp2220VersionsTable 1 }

Cdcp2220VersionsEntry ::= SEQUENCE
{
    cdcp2220VersionsIndex       Cdcp2220VersionsIdx,
    cdcp2220VersionsDescription DisplayString,
    cdcp2220VersionsVersion     DisplayString
}

cdcp2220VersionsIndex OBJECT-TYPE
    SYNTAX        Cdcp2220VersionsIdx
    MAX-ACCESS    read-only
    STATUS        current
    DESCRIPTION
        "Projector Configuration index to which the parameters in this
         row apply."
    ::= { cdcp2220VersionsEntry 1 }

cdcp2220VersionsDescription OBJECT-TYPE
    SYNTAX        DisplayString (SIZE(0..63))
    MAX-ACCESS    read-only
    STATUS        current
    DESCRIPTION
        "Component which this version entry maps to."
    ::= { cdcp2220VersionsEntry 2 }

cdcp2220VersionsVersion OBJECT-TYPE
    SYNTAX        DisplayString (SIZE(0..63))
    MAX-ACCESS    read-only
    STATUS        current
    DESCRIPTION
        "The version or serial number of the component this row
         represents.
         ."
    ::= { cdcp2220VersionsEntry 3 }

cdcp2220SerialNumberTable OBJECT-TYPE
    SYNTAX        SEQUENCE OF Cdcp2220SerialNumberEntry
    MAX-ACCESS    not-accessible
    STATUS        current
    DESCRIPTION
        "A table listing the serial numbers of the projectors hardware
         and software components."
    ::= { cdcp2220Config 2 }

cdcp2220SerialNumberEntry OBJECT-TYPE
    SYNTAX        Cdcp2220SerialNumberEntry
    MAX-ACCESS    not-accessible
    STATUS        current
    DESCRIPTION
        "The projector component description and serial number."
    INDEX
        { cdcp2220SerialNumberIndex }
    ::= { cdcp2220SerialNumberTable 1 }

Cdcp2220SerialNumberEntry ::= SEQUENCE
{
    cdcp2220SerialNumberIndex       Cdcp2220SerialNumberIdx,
    cdcp2220SerialNumberDescription DisplayString,
    cdcp2220SerialNumberVersion     DisplayString
}

cdcp2220SerialNumberIndex OBJECT-TYPE
    SYNTAX        Cdcp2220SerialNumberIdx
    MAX-ACCESS    read-only
    STATUS        current
    DESCRIPTION
        "Projector Configuration index to which the parameters in this
         row apply."
    ::= { cdcp2220SerialNumberEntry 1 }

cdcp2220SerialNumberDescription OBJECT-TYPE
    SYNTAX        DisplayString (SIZE(0..63))
    MAX-ACCESS    read-only
    STATUS        current
    DESCRIPTION
        "Component which this serial number entry maps to."
    ::= { cdcp2220SerialNumberEntry 2 }

cdcp2220SerialNumberVersion OBJECT-TYPE
    SYNTAX        DisplayString (SIZE(0..63))
    MAX-ACCESS    read-only
    STATUS        current
    DESCRIPTION
        "The serial number of the component this row represents. ."
    ::= { cdcp2220SerialNumberEntry 3 }

cdcp2220Priv OBJECT IDENTIFIER ::= { cdcp2220Config 3 }

cdcp2220CertificateIcp OBJECT-TYPE
    SYNTAX        X509Certificate
    MAX-ACCESS    read-only
    STATUS        current
    DESCRIPTION
        "This object contains the Interface Certificate.  The object
         value must be the ASN.1 DER encoding of the MTA manufacturer's
         X.509 public key certificate. ,contains the MTA's MAC  address.
         It The MTA Manufacturer Certificate is issued to each MTA
         manufacturer and is installed into each MTA at the time of
         manufacture or with a secure code download. The specific
         requirements related to this certificate are defined in  the
         Security specification."
    REFERENCE
        "Security Specification."
    ::= { cdcp2220Priv 1 }

cdcp2220CertificateLD OBJECT-TYPE
    SYNTAX        X509Certificate
    MAX-ACCESS    read-only
    STATUS        current
    DESCRIPTION
        "ASN.1 DER encoding of the MTA's X.509 public-key  certificate
         issued by the manufacturer and installed  into the embedded-MTA
         in the factory. This certificate,  called Certificate, cannot
         be updated by the provisioning server."
    ::= { cdcp2220Priv 2 }

cdcp2220IcpType OBJECT-TYPE
    SYNTAX        INTEGER {
        -- Unknown
        na(1),
        -- 8 MegaByte flash
        series2mb8(2),
        -- 16 MegaByte flash
        series2mb16(3),
	-- ICP 1.5 - 16 MegaByte flash
	series2Icp15mb16(4)

    }
    MAX-ACCESS    read-only
    STATUS        current
    DESCRIPTION
        "Returns the ICP type:
         Series2 - 8 MB flash 
         Series2 - 16 MB flash
         Series2 - ICP 1.5 - 16 MB flash"
    ::= { cdcp2220Config 4 }

cdcp2220DmdType OBJECT-TYPE
    SYNTAX        INTEGER {
        -- Not attached or unknown
        na(1),
        -- .98 inch DMD
        dc2k98(2),
        -- 2k 1.2 inch DMD
        dc2k12(3),
        -- 4k 1.38 inch DMD
        dc4k138(4)
    }
    MAX-ACCESS    read-only
    STATUS        current
    DESCRIPTION
        "Returns the DMD Type:
         2K - 0.98 inch DMD
         2K - 1.2 inch DMD
         4K - 1.38 inch DMD"
    ::= { cdcp2220Config 5 }

cdcp2220SatelliteType OBJECT IDENTIFIER ::= { cdcp2220Config 6 }

cdcp2220RedSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp2220SatelliteType 1 }

cdcp2220GreenSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp2220SatelliteType 2 }

cdcp2220BlueSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp2220SatelliteType 3 }

cdcp2220Peripherals OBJECT IDENTIFIER ::= { cdcp2220Config 7 }

cdcp2220IlsInstalled OBJECT-TYPE
    SYNTAX        TruthValue
    MAX-ACCESS    read-only
    STATUS        current
    DESCRIPTION
        "Returns true if ILS is installed otherwise returns false."
    ::= { cdcp2220Peripherals 1 }

cdcp2220LdInstalled OBJECT-TYPE
    SYNTAX        TruthValue
    MAX-ACCESS    read-only
    STATUS        current
    DESCRIPTION
        "Returns true if LD is installed otherwise returns false."
    ::= { cdcp2220Peripherals 2 }

cdcp2220MediaBlockInstalled OBJECT-TYPE
    SYNTAX        TruthValue
    MAX-ACCESS    read-only
    STATUS        current
    DESCRIPTION
        "Returns true if MediaBlock is installed otherwise returns
         false."
    ::= { cdcp2220Peripherals 3 }

cdcp2220Status OBJECT IDENTIFIER ::= { cp2220 2 }

-- ====================================================================
-- 
-- Security status group

cdcp2220SecurityStatus OBJECT IDENTIFIER ::= { cdcp2220Status 1 }

cdcp2220SecurityArmed OBJECT-TYPE
    SYNTAX        INTEGER {
        armed(1),
        notArmed(2),
        na(3)
    }
    MAX-ACCESS    read-only
    STATUS        current
    DESCRIPTION
        "Security enclosure armed."
    ::= { cdcp2220SecurityStatus 1 }

cdcp2220SecurityTamper OBJECT-TYPE
    SYNTAX        INTEGER {
        tamper(1),
        secure(2),
        na(3)
    }
    MAX-ACCESS    read-only
    STATUS        current
    DESCRIPTION
        "Security enclosure tamper."
    ::= { cdcp2220SecurityStatus 2 }

cdcp2220MarriageActive OBJECT-TYPE
    SYNTAX        INTEGER {
        married(1),
        marriageBroken(2),
        na(3)
    }
    MAX-ACCESS    read-only
    STATUS        current
    DESCRIPTION
        "Marriage State,  When marriage is broken, no encrypted content
         can be played."
    ::= { cdcp2220SecurityStatus 3 }

cdcp2220PhysicalMarriageTamper OBJECT-TYPE
    SYNTAX        INTEGER {
        tampered(1),
        secure(2),
        na(3)
    }
    MAX-ACCESS    read-only
    STATUS        current
    DESCRIPTION
        "Physical Marriage State, Removal of any board within the card
         cage will cause a Physical tamper."
    ::= { cdcp2220SecurityStatus 4 }

cdcp2220LogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the LD board or Image Media Block."
    ::= { cdcp2220SecurityStatus 5 }

cdcp2220SoftwareCertZeroization OBJECT-TYPE
    SYNTAX        INTEGER {
        zeroed(1),
        ok(2),
        na(3)
    }
    MAX-ACCESS    read-only
    STATUS        current
    DESCRIPTION
        "Certificate State, A zeroed certificate state indicates  that
         a tamper has occurred on the LD board."
    ::= { cdcp2220SecurityStatus 6 }

cdcp2220ServiceDoorTamper OBJECT-TYPE
    SYNTAX        INTEGER {
        tamper(1),
        secure(2),
        na(3)
    }
    MAX-ACCESS    read-only
    STATUS        current
    DESCRIPTION
        "Service door to light engine compartment"
    ::= { cdcp2220SecurityStatus 7 }

cdcp2220TopEnclosureOpen OBJECT-TYPE
    SYNTAX        INTEGER {
        tamper(1),
        secure(2),
        na(3)
    }
    MAX-ACCESS    read-only
    STATUS        current
    DESCRIPTION
        "Security enclosure state, top side."
    ::= { cdcp2220SecurityStatus 8 }

cdcp2220BottomEnclosureOpen OBJECT-TYPE
    SYNTAX        INTEGER {
        tamper(1),
        secure(2),
        na(3)
    }
    MAX-ACCESS    read-only
    STATUS        current
    DESCRIPTION
        "Security enclosure state, top side."
    ::= { cdcp2220SecurityStatus 9 }

cdcp2220SecurityBatteryEvent OBJECT-TYPE
    SYNTAX        INTEGER {
        failed(1),
        ok(2),
        na(3)
    }
    MAX-ACCESS    read-only
    STATUS        current
    DESCRIPTION
        "Battery failed"
    ::= { cdcp2220SecurityStatus 10 }

cdcp2220BatteryLow OBJECT-TYPE
    SYNTAX        INTEGER {
        low(1),
        ok(2),
        na(3)
    }
    MAX-ACCESS    read-only
    STATUS        current
    DESCRIPTION
        "Battery state."
    ::= { cdcp2220SecurityStatus 11 }

cdcp2220SecurityLog OBJECT-TYPE
    SYNTAX        INTEGER {
        ok(1),
        warning(2),
        error(3),
        na(4)
    }
    MAX-ACCESS    read-only
    STATUS        current
    DESCRIPTION
        "The Security Log Warning indicates that there are  less than
         100 log entry locations available before  unread log entries
         will be overwritten.

         The Security Log Error indicates that there is no  more room to
         write log entries.

         When this warning/error is active, the Server needs  to extract
         the log data (via ASM/TLS session) from  the LD Security Log.
         Reads of the security log by any other entity/means will not
         impact this warning."
    ::= { cdcp2220SecurityStatus 12 }
    
    
cdcp2220IMBSecurityArmed OBJECT-TYPE
    SYNTAX        INTEGER {
        armed(1),
        notArmed(2),
        na(3)
    }
    MAX-ACCESS    read-only
    STATUS        current
    DESCRIPTION
        "IMB Security enclosure armed."
    ::= { cdcp2220SecurityStatus 13 }

cdcp2220IMBSecurityTamper OBJECT-TYPE
    SYNTAX        INTEGER {
        tamper(1),
        secure(2),
        na(3)
    }
    MAX-ACCESS    read-only
    STATUS        current
    DESCRIPTION
        "IMB Security enclosure tamper."
    ::= { cdcp2220SecurityStatus 14 }

cdcp2220IMBMarriageActive OBJECT-TYPE
    SYNTAX        INTEGER {
        married(1),
        marriageBroken(2),
        na(3)
    }
    MAX-ACCESS    read-only
    STATUS        current
    DESCRIPTION
        "IMB Marriage State,  When marriage is broken, no encrypted content
         can be played."
    ::= { cdcp2220SecurityStatus 15 }

cdcp2220IMBPhysicalMarriageTamper OBJECT-TYPE
    SYNTAX        INTEGER {
        tampered(1),
        secure(2),
        na(3)
    }
    MAX-ACCESS    read-only
    STATUS        current
    DESCRIPTION
        "IMB Physical Marriage State, Removal of any board within the card
         cage will cause a Physical tamper."
    ::= { cdcp2220SecurityStatus 16 }

cdcp2220IMBLogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the Image Media Block."
    ::= { cdcp2220SecurityStatus 17 }
    
cdcp2220IMBServiceDoorArmed OBJECT-TYPE
    SYNTAX        INTEGER {
        armed(1),
        tamper(2),
        na(3)
    }
    MAX-ACCESS    read-only
    STATUS        current
    DESCRIPTION
        "Service door to light engine compartment"
    ::= { cdcp2220SecurityStatus 18 }

cdcp2220IMBServiceDoorTamper OBJECT-TYPE
    SYNTAX        INTEGER {
        tamper(1),
        secure(2),
        na(3)
    }
    MAX-ACCESS    read-only
    STATUS        current
    DESCRIPTION
        "IMB Service door to light engine compartment"
    ::= { cdcp2220SecurityStatus 19 }

cdcp2220IMBBatteryLow OBJECT-TYPE
    SYNTAX        INTEGER {
        low(1),
        ok(2),
        na(3)
    }
    MAX-ACCESS    read-only
    STATUS        current
    DESCRIPTION
        "IMB Battery state."
    ::= { cdcp2220SecurityStatus 20 }
    
cdcp2220IMBICPCommunicationError OBJECT-TYPE
    SYNTAX        INTEGER {
        error(1),
        ok(2),
        na(3)
    }
    MAX-ACCESS    read-only
    STATUS        current
    DESCRIPTION
        "IMB Battery state."
    ::= { cdcp2220SecurityStatus 21 }

-- ====================================================================
-- 
-- Sensor tables

cdcp2220Sensors OBJECT IDENTIFIER ::= { cdcp2220Status 2 }

cdcp2220TempSensorsTable OBJECT-TYPE
    SYNTAX        SEQUENCE OF Cdcp2220TempSensorsEntry
    MAX-ACCESS    not-accessible
    STATUS        current
    DESCRIPTION
        "Table of temperature sensors and their values."
    ::= { cdcp2220Sensors 1 }

cdcp2220TempSensorsEntry OBJECT-TYPE
    SYNTAX        Cdcp2220TempSensorsEntry
    MAX-ACCESS    not-accessible
    STATUS        current
    DESCRIPTION
        "An entry containing a device and its statistics."
    INDEX
        { cdcp2220TempSensorsIndex }
    ::= { cdcp2220TempSensorsTable 1 }

Cdcp2220TempSensorsEntry ::= SEQUENCE
{
    cdcp2220TempSensorsIndex      Integer32,
    cdcp2220TempSensorsDevice     DisplayString,
    cdcp2220TempSensorsDiodeError TruthValue,
    cdcp2220TempSensorsLowerLimit TruthValue,
    cdcp2220TempSensorsUpperLimit TruthValue,
    cdcp2220TempSensorsValue      Gauge32
}

cdcp2220TempSensorsIndex OBJECT-TYPE
    SYNTAX        Integer32 (0..65535)
    MAX-ACCESS    read-only
    STATUS        current
    DESCRIPTION
        "Reference index for each observed device."
    ::= { cdcp2220TempSensorsEntry 1 }

cdcp2220TempSensorsDevice OBJECT-TYPE
    SYNTAX        DisplayString (SIZE(0..63))
    MAX-ACCESS    read-only
    STATUS        current
    DESCRIPTION
        "The name of the temperature sensor we are reading."
    ::= { cdcp2220TempSensorsEntry 2 }

cdcp2220TempSensorsDiodeError OBJECT-TYPE
    SYNTAX        TruthValue
    MAX-ACCESS    read-only
    STATUS        current
    DESCRIPTION
        "True if a diode error has occurred."
    ::= { cdcp2220TempSensorsEntry 3 }

cdcp2220TempSensorsLowerLimit OBJECT-TYPE
    SYNTAX        TruthValue
    MAX-ACCESS    read-only
    STATUS        current
    DESCRIPTION
        "True if the sensor has breached it's lower limit."
    ::= { cdcp2220TempSensorsEntry 4 }

cdcp2220TempSensorsUpperLimit OBJECT-TYPE
    SYNTAX        TruthValue
    MAX-ACCESS    read-only
    STATUS        current
    DESCRIPTION
        "True if the sensor has breached it's upper limit."
    ::= { cdcp2220TempSensorsEntry 5 }

cdcp2220TempSensorsValue OBJECT-TYPE
    SYNTAX        Gauge32
    MAX-ACCESS    read-only
    STATUS        current
    DESCRIPTION
        "The temperature of this sensor in Celsius"
    ::= { cdcp2220TempSensorsEntry 6 }

cdcp2220FanSensorsTable OBJECT-TYPE
    SYNTAX        SEQUENCE OF Cdcp2220FanSensorsEntry
    MAX-ACCESS    not-accessible
    STATUS        current
    DESCRIPTION
        "Table of fan sensors and their values."
    ::= { cdcp2220Sensors 2 }

cdcp2220FanSensorsEntry OBJECT-TYPE
    SYNTAX        Cdcp2220FanSensorsEntry
    MAX-ACCESS    not-accessible
    STATUS        current
    DESCRIPTION
        "An entry containing a device and its statistics."
    INDEX
        { cdcp2220FanSensorsIndex }
    ::= { cdcp2220FanSensorsTable 1 }

Cdcp2220FanSensorsEntry ::= SEQUENCE
{
    cdcp2220FanSensorsIndex   Integer32,
    cdcp2220FanSensorsDevice  DisplayString,
    cdcp2220FanSensorsFault   TruthValue,
    cdcp2220FanSensorsTooSlow TruthValue,
    cdcp2220FanSensorsValue   Gauge32
}

cdcp2220FanSensorsIndex OBJECT-TYPE
    SYNTAX        Integer32 (0..65535)
    MAX-ACCESS    read-only
    STATUS        current
    DESCRIPTION
        "Reference index for each observed device."
    ::= { cdcp2220FanSensorsEntry 1 }

cdcp2220FanSensorsDevice OBJECT-TYPE
    SYNTAX        DisplayString (SIZE(0..63))
    MAX-ACCESS    read-only
    STATUS        current
    DESCRIPTION
        "The name of the fan sensor we are reading."
    ::= { cdcp2220FanSensorsEntry 2 }

cdcp2220FanSensorsFault OBJECT-TYPE
    SYNTAX        TruthValue
    MAX-ACCESS    read-only
    STATUS        current
    DESCRIPTION
        "True if the fan has faulted."
    ::= { cdcp2220FanSensorsEntry 3 }

cdcp2220FanSensorsTooSlow OBJECT-TYPE
    SYNTAX        TruthValue
    MAX-ACCESS    read-only
    STATUS        current
    DESCRIPTION
        "True if a fan speed error has occurred with this fan."
    ::= { cdcp2220FanSensorsEntry 4 }

cdcp2220FanSensorsValue OBJECT-TYPE
    SYNTAX        Gauge32
    MAX-ACCESS    read-only
    STATUS        current
    DESCRIPTION
        "The rotation speed of the fan in RPM."
    ::= { cdcp2220FanSensorsEntry 5 }

cdcp2220InterlockSensorsTable OBJECT-TYPE
    SYNTAX        SEQUENCE OF Cdcp2220InterlockSensorsEntry
    MAX-ACCESS    not-accessible
    STATUS        current
    DESCRIPTION
        "Table of interlock sensors and their value."
    ::= { cdcp2220Sensors 3 }

cdcp2220InterlockSensorsEntry OBJECT-TYPE
    SYNTAX        Cdcp2220InterlockSensorsEntry
    MAX-ACCESS    not-accessible
    STATUS        current
    DESCRIPTION
        "An entry containing a device and its statistics."
    INDEX
        { cdcp2220InterlockSensorsIndex }
    ::= { cdcp2220InterlockSensorsTable 1 }

Cdcp2220InterlockSensorsEntry ::= SEQUENCE
{
    cdcp2220InterlockSensorsIndex  Integer32,
    cdcp2220InterlockSensorsDevice DisplayString,
    cdcp2220InterlockSensorsValue  INTEGER
}

cdcp2220InterlockSensorsIndex OBJECT-TYPE
    SYNTAX        Integer32 (0..65535)
    MAX-ACCESS    read-only
    STATUS        current
    DESCRIPTION
        "Reference index for each observed device."
    ::= { cdcp2220InterlockSensorsEntry 1 }

cdcp2220InterlockSensorsDevice OBJECT-TYPE
    SYNTAX        DisplayString (SIZE(0..63))
    MAX-ACCESS    read-only
    STATUS        current
    DESCRIPTION
        "The name of the interlock sensor we are reading."
    ::= { cdcp2220InterlockSensorsEntry 2 }

cdcp2220InterlockSensorsValue OBJECT-TYPE
    SYNTAX        INTEGER {
        open(1),
        closed(2),
        troubleOpen(3),
        troubleClosed(4)
    }
    MAX-ACCESS    read-only
    STATUS        current
    DESCRIPTION
        "The status of this interlock."
    ::= { cdcp2220InterlockSensorsEntry 3 }

-- ====================================================================
-- 
-- System health table, reports diagnostic test results.

cdcp2220SystemHealthTable OBJECT-TYPE
    SYNTAX        SEQUENCE OF Cdcp2220SystemHealthEntry
    MAX-ACCESS    not-accessible
    STATUS        current
    DESCRIPTION
        "Table of diagnostic tests and their results"
    ::= { cdcp2220Status 3 }

cdcp2220SystemHealthEntry OBJECT-TYPE
    SYNTAX        Cdcp2220SystemHealthEntry
    MAX-ACCESS    not-accessible
    STATUS        current
    DESCRIPTION
        "Each row respresents a diagnostic test and the result."
    INDEX
        { cdcp2220SystemHealthIndex }
    ::= { cdcp2220SystemHealthTable 1 }

Cdcp2220SystemHealthEntry ::= SEQUENCE
{
    cdcp2220SystemHealthIndex  Integer32,
    cdcp2220SystemHealthName   DisplayString,
    cdcp2220SystemHealthResult DisplayString
}

cdcp2220SystemHealthIndex OBJECT-TYPE
    SYNTAX        Integer32 (0..65535)
    MAX-ACCESS    read-only
    STATUS        current
    DESCRIPTION
        "Reference index for each observed test."
    ::= { cdcp2220SystemHealthEntry 1 }

cdcp2220SystemHealthName OBJECT-TYPE
    SYNTAX        DisplayString (SIZE(0..127))
    MAX-ACCESS    read-only
    STATUS        current
    DESCRIPTION
        "Name of the diagnostic being reported."
    ::= { cdcp2220SystemHealthEntry 2 }

cdcp2220SystemHealthResult OBJECT-TYPE
    SYNTAX        DisplayString (SIZE(0..127))
    MAX-ACCESS    read-only
    STATUS        current
    DESCRIPTION
        "Result of diagnostic."
    ::= { cdcp2220SystemHealthEntry 3 }

cdcp2220LensTable OBJECT-TYPE
    SYNTAX        SEQUENCE OF Cdcp2220LensEntry
    MAX-ACCESS    not-accessible
    STATUS        current
    DESCRIPTION
        "A table listing the lens entries."
    ::= { cdcp2220Status 4 }

cdcp2220LensEntry OBJECT-TYPE
    SYNTAX        Cdcp2220LensEntry
    MAX-ACCESS    not-accessible
    STATUS        current
    DESCRIPTION
        "The number of hours the projector has operated."
    INDEX
        { cdcp2220LensIdx }
    ::= { cdcp2220LensTable 1 }

Cdcp2220LensEntry ::= SEQUENCE
{
    cdcp2220LensIdx          Cdcp2220LensIndex,
    cdcp2220LensClass        DisplayString,
    cdcp2220LensType         DisplayString,
    cdcp2220LensSerialNumber DisplayString,
    cdcp2220LensStatus       INTEGER
}

cdcp2220LensIdx OBJECT-TYPE
    SYNTAX        Cdcp2220LensIndex (0..65535)
    MAX-ACCESS    read-only
    STATUS        current
    DESCRIPTION
        "Projector Lens index.  Each entry represents a various
         attributes of the Lens"
    ::= { cdcp2220LensEntry 1 }

cdcp2220LensClass OBJECT-TYPE
    SYNTAX        DisplayString (SIZE(0..255))
    MAX-ACCESS    read-only
    STATUS        current
    DESCRIPTION
        "Lens Class (Primary, Secondry...)"
    ::= { cdcp2220LensEntry 2 }

cdcp2220LensType OBJECT-TYPE
    SYNTAX        DisplayString (SIZE(0..255))
    MAX-ACCESS    read-only
    STATUS        current
    DESCRIPTION
        "Lens Type"
    ::= { cdcp2220LensEntry 3 }

cdcp2220LensSerialNumber OBJECT-TYPE
    SYNTAX        DisplayString (SIZE(0..255))
    MAX-ACCESS    read-only
    STATUS        current
    DESCRIPTION
        "Lens Serial Number"
    ::= { cdcp2220LensEntry 4 }

cdcp2220LensStatus OBJECT-TYPE
    SYNTAX        INTEGER {
        in(1),
        out(2)
    }
    MAX-ACCESS    read-only
    STATUS        current
    DESCRIPTION
        "Lens Status"
    ::= { cdcp2220LensEntry 5 }

cdcp2220System OBJECT IDENTIFIER ::= { cdcp2220Status 5 }

cdcp2220Tpc OBJECT IDENTIFIER ::= { cdcp2220System 1 }

cdcp2220TpcType OBJECT-TYPE
    SYNTAX        OCTET STRING
    MAX-ACCESS    read-only
    STATUS        current
    DESCRIPTION
        "Returns the TPC Type:
         TPC-660E TPC-650H"
    ::= { cdcp2220Tpc 1 }

cdcp2220TpcOs OBJECT-TYPE
    SYNTAX        OCTET STRING
    MAX-ACCESS    read-only
    STATUS        current
    DESCRIPTION
        "Returns the TPC OS Image"
    ::= { cdcp2220Tpc 2 }

cdcp2220TpcDiskSpaceAvailable OBJECT-TYPE
    SYNTAX        Integer32
    MAX-ACCESS    read-only
    STATUS        current
    DESCRIPTION
        "Returns the available TPC Disk Space"
    ::= { cdcp2220Tpc 3 }

cdcp2220TpcDiskSpaceUsed OBJECT-TYPE
    SYNTAX        Integer32
    MAX-ACCESS    read-only
    STATUS        current
    DESCRIPTION
        "Returns the TPC Disk Space, Used (MB)"
    ::= { cdcp2220Tpc 4 }

cdcp2220TpcMemorySpaceAvailable OBJECT-TYPE
    SYNTAX        Integer32
    MAX-ACCESS    read-only
    STATUS        current
    DESCRIPTION
        "Returns the available TPC Memory RAM (KB)"
    ::= { cdcp2220Tpc 5 }

cdcp2220Power OBJECT IDENTIFIER ::= { cdcp2220System 2 }

cdcp2220LvpsACok OBJECT-TYPE
    SYNTAX        INTEGER {
        -- OK
        yes(1),
        -- Fail
        no(2),
        -- Not available
        na(3)
    }
    MAX-ACCESS    read-only
    STATUS        current
    DESCRIPTION
        "Returns the AC OK signal state
         1 = yes
         2 = no
         3 = Not available"
    ::= { cdcp2220Power 1 }

cdcp2220LvpsDCok OBJECT-TYPE
    SYNTAX        INTEGER {
        -- OK
        yes(1),
        -- Fail
        no(2),
        -- Not available
        na(3)
    }
    MAX-ACCESS    read-only
    STATUS        current
    DESCRIPTION
        "Returns the CC OK signal state
         1 = yes
         2 = no
         3 = Not available"
    ::= { cdcp2220Power 2 }

cdcp2220PibPowerGoodVid OBJECT-TYPE
    SYNTAX        INTEGER {
        -- OK
        yes(1),
        -- Fail
        no(2),
        -- Not available
        na(3)
    }
    MAX-ACCESS    read-only
    STATUS        current
    DESCRIPTION
        "Returns the Power Good Vid signal state
         1 = yes
         2 = no
         3 = Not available"
    ::= { cdcp2220Power 3 }

cdcp2220PibPowerGood1v2and2v5 OBJECT-TYPE
    SYNTAX        INTEGER {
        -- OK
        yes(1),
        -- Fail
        no(2),
        -- Not available
        na(3)
    }
    MAX-ACCESS    read-only
    STATUS        current
    DESCRIPTION
        "Returns the PIB PowerGood signal for the 1.2v and 2.5v rails 1
         = yes
         2 = no
         3 = Not available"
    ::= { cdcp2220Power 4 }

cdcp2220PibPowerGood1v8and3v3 OBJECT-TYPE
    SYNTAX        INTEGER {
        -- OK
        yes(1),
        -- Fail
        no(2),
        -- Not available
        na(3)
    }
    MAX-ACCESS    read-only
    STATUS        current
    DESCRIPTION
        "Returns the PIB PowerGood signal for the 1.8v and 3.3v rails 1
         = yes
         2 = no
         3 = Not available"
    ::= { cdcp2220Power 5 }

cdcp2220PibPowerGood24vEXT OBJECT-TYPE
    SYNTAX        INTEGER {
        -- OK
        yes(1),
        -- Fail
        no(2),
        -- Not available
        na(3)
    }
    MAX-ACCESS    read-only
    STATUS        current
    DESCRIPTION
        "Returns the PIB PowerGood signal for the 24v External 1 = yes
         2 = no
         3 = Not available"
    ::= { cdcp2220Power 6 }

cdcp2220PibPowerGood24vSTBY OBJECT-TYPE
    SYNTAX        INTEGER {
        -- OK
        yes(1),
        -- Fail
        no(2),
        -- Not available
        na(3)
    }
    MAX-ACCESS    read-only
    STATUS        current
    DESCRIPTION
        "Returns the PIB PowerGood signal for the 24v Standby. 1 = yes
         2 = no
         3 = Not available"
    ::= { cdcp2220Power 7 }

cdcp2220Icp1v2 OBJECT-TYPE
    SYNTAX        OCTET STRING (SIZE(1..10))
    MAX-ACCESS    read-only
    STATUS        current
    DESCRIPTION
        "Returns the ICP 1.2v rail measurements or NA if in Standby"
    ::= { cdcp2220Power 8 }

cdcp2220Icp1v8 OBJECT-TYPE
    SYNTAX        OCTET STRING (SIZE(1..10))
    MAX-ACCESS    read-only
    STATUS        current
    DESCRIPTION
        "Returns the ICP 1.8v rail measurements or NA if in Standby"
    ::= { cdcp2220Power 9 }

cdcp2220Icp2v5 OBJECT-TYPE
    SYNTAX        OCTET STRING (SIZE(1..10))
    MAX-ACCESS    read-only
    STATUS        current
    DESCRIPTION
        "Returns the ICP 2.5v rail measurements or NA if in Standby"
    ::= { cdcp2220Power 10 }

cdcp2220Icp3v3 OBJECT-TYPE
    SYNTAX        OCTET STRING (SIZE(1..10))
    MAX-ACCESS    read-only
    STATUS        current
    DESCRIPTION
        "Returns the ICP 3.3v rail measurements or NA if in Standby"
    ::= { cdcp2220Power 11 }

cdcp2220IcpCommunicating OBJECT-TYPE
    SYNTAX        TruthValue
    MAX-ACCESS    read-only
    STATUS        current
    DESCRIPTION
        "Returns IPC State:
         True = Communicating False = Not Communicating"
    ::= { cdcp2220System 3 }

cdcp2220LinkDecryptor OBJECT IDENTIFIER ::= { cdcp2220System 4 }

cdcp2220LdCommunicating OBJECT-TYPE
    SYNTAX        TruthValue
    MAX-ACCESS    read-only
    STATUS        current
    DESCRIPTION
        "Returns the ICP connection state. True = Communicating False =
         Not Communicating"
    ::= { cdcp2220LinkDecryptor 1 }

cdcp2220LdLink0 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link states:
         No Source Decryption Not Active Decryption Active Decryption
         Error Unknown"
    ::= { cdcp2220LinkDecryptor 2 }

cdcp2220LdLink1 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link1 states:
         No Source Decryption Not Active Decryption Active Decryption
         Error Unknown"
    ::= { cdcp2220LinkDecryptor 3 }

cdcp2220LdLink2 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link2 states:
         No Source Decryption Not Active Decryption Active Decryption
         Error Unknown"
    ::= { cdcp2220LinkDecryptor 4 }

cdcp2220LdLink3 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link3 states:
         No Source Decryption Not Active Decryption Active Decryption
         Error Unknown"
    ::= { cdcp2220LinkDecryptor 5 }

cdcp2220Icp OBJECT-IDENTITY
    STATUS        current
    DESCRIPTION
        "ICP related objects"
    ::= { cdcp2220System 5 }

cdcp2220IcpDiskSpaceTotal OBJECT-TYPE
    SYNTAX        Integer32
    MAX-ACCESS    read-only
    STATUS        current
    DESCRIPTION
        "Returns the available ICP Disk Space (KB)"
    ::= { cdcp2220Icp 1 }

cdcp2220IcpDiskSpaceFree OBJECT-TYPE
    SYNTAX        Integer32
    MAX-ACCESS    read-only
    STATUS        current
    DESCRIPTION
        "Returns the ICP Disk Space, Free (KB)"
    ::= { cdcp2220Icp 2 }

cdcp2220StatusPeripherals OBJECT IDENTIFIER ::= { cdcp2220Status 6 }

END
