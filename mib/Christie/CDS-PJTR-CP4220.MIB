CDS-PJTR-CP4220 DEFINITIONS ::= BEGIN

IMPORTS
    cdEsProjector
        FROM CDS-SMI
    Gauge32, Integer32, MODULE-IDENTITY, OBJECT-IDENTITY, OBJECT-TYPE
        FROM SNMPv2-SMI
    DisplayString, TEXTUAL-CONVENTION, TruthValue
        FROM SNMPv2-TC
    ;

cp4220 MODULE-IDENTITY
    LAST-UPDATED  "201008031914Z" -- August 03, 2010
    ORGANIZATION
        "Christie Digital Systems, Inc."
    CONTACT-INFO
        "Christie Digital Systems
         Customer Service

         Postal:     10550 Camden Drive
         Cypress, Ca 90630
         USA

         Tel:        +1 800 221-8025

         E-mail:     support@christiedigital.com"
    DESCRIPTION
        "The MIB module for CDS Entertainment Solutions CP4220 Cinema
         projector.
         iso(1).org(3).dod(6).internet(1).private(4).enterprises(1)
         .christiedigital(25766)
         .christieDigitalProduct(1)
         .cdEs(12).cdEsProjector(1)"
    REVISION      "201009141437Z" -- September 14, 2010
    DESCRIPTION
        "Added support for ICP Disk space"
    REVISION      "201008031933Z" -- August 03, 2010
    DESCRIPTION
	"First revision"
    REVISION	  "201103301915Z" -- March 30, 2011
    DESCRIPTION
	"Updated: IcpType to include ICP 1.5 - 16 MegaByte Flash"        

    ::= { cdEsProjector 5 }

-- ====================================================================
-- 
-- Lens Table - a table of lens entries

Cdcp4220LensIndex ::= TEXTUAL-CONVENTION
    STATUS        current
    DESCRIPTION
        "A value used to index the Lens table."
    SYNTAX        Integer32

-- ====================================================================
-- 
-- Versions - a table of serial numbers of install sw/hw components

Cdcp4220SerialNumberIdx ::= TEXTUAL-CONVENTION
    STATUS        current
    DESCRIPTION
        "A value used to index projector serial numbers."
    SYNTAX        Integer32 (1..64)

-- ====================================================================
-- 
-- Versions - a table of versions of install sw/hw components

Cdcp4220VersionsIdx ::= TEXTUAL-CONVENTION
    STATUS        current
    DESCRIPTION
        "A value used to index projector versions."
    SYNTAX        Integer32 (1..64)

-- ====================================================================
-- 
-- Admin only

X509Certificate ::= TEXTUAL-CONVENTION
    STATUS        current
    DESCRIPTION
        "An X509 digital certificate encoded as an ASN.1 DER object."
    SYNTAX        OCTET STRING (SIZE(0..4096))

cdcp4220Config OBJECT IDENTIFIER ::= { cp4220 1 }

cdcp4220VersionsTable OBJECT-TYPE
    SYNTAX        SEQUENCE OF Cdcp4220VersionsEntry
    MAX-ACCESS    not-accessible
    STATUS        current
    DESCRIPTION
        "A table listing the versions of the projectors hardware and
         software components."
    ::= { cdcp4220Config 1 }

cdcp4220VersionsEntry OBJECT-TYPE
    SYNTAX        Cdcp4220VersionsEntry
    MAX-ACCESS    not-accessible
    STATUS        current
    DESCRIPTION
        "The projector component description and version."
    INDEX
        { cdcp4220VersionsIndex }
    ::= { cdcp4220VersionsTable 1 }

Cdcp4220VersionsEntry ::= SEQUENCE
{
    cdcp4220VersionsIndex       Cdcp4220VersionsIdx,
    cdcp4220VersionsDescription DisplayString,
    cdcp4220VersionsVersion     DisplayString
}

cdcp4220VersionsIndex OBJECT-TYPE
    SYNTAX        Cdcp4220VersionsIdx
    MAX-ACCESS    read-only
    STATUS        current
    DESCRIPTION
        "Projector Configuration index to which the parameters in this
         row apply."
    ::= { cdcp4220VersionsEntry 1 }

cdcp4220VersionsDescription OBJECT-TYPE
    SYNTAX        DisplayString (SIZE(0..63))
    MAX-ACCESS    read-only
    STATUS        current
    DESCRIPTION
        "Component which this version entry maps to."
    ::= { cdcp4220VersionsEntry 2 }

cdcp4220VersionsVersion OBJECT-TYPE
    SYNTAX        DisplayString (SIZE(0..63))
    MAX-ACCESS    read-only
    STATUS        current
    DESCRIPTION
        "The version or serial number of the component this row
         represents.
         ."
    ::= { cdcp4220VersionsEntry 3 }

cdcp4220SerialNumberTable OBJECT-TYPE
    SYNTAX        SEQUENCE OF Cdcp4220SerialNumberEntry
    MAX-ACCESS    not-accessible
    STATUS        current
    DESCRIPTION
        "A table listing the serial numbers of the projectors hardware
         and software components."
    ::= { cdcp4220Config 2 }

cdcp4220SerialNumberEntry OBJECT-TYPE
    SYNTAX        Cdcp4220SerialNumberEntry
    MAX-ACCESS    not-accessible
    STATUS        current
    DESCRIPTION
        "The projector component description and serial number."
    INDEX
        { cdcp4220SerialNumberIndex }
    ::= { cdcp4220SerialNumberTable 1 }

Cdcp4220SerialNumberEntry ::= SEQUENCE
{
    cdcp4220SerialNumberIndex       Cdcp4220SerialNumberIdx,
    cdcp4220SerialNumberDescription DisplayString,
    cdcp4220SerialNumberVersion     DisplayString
}

cdcp4220SerialNumberIndex OBJECT-TYPE
    SYNTAX        Cdcp4220SerialNumberIdx
    MAX-ACCESS    read-only
    STATUS        current
    DESCRIPTION
        "Projector Configuration index to which the parameters in this
         row apply."
    ::= { cdcp4220SerialNumberEntry 1 }

cdcp4220SerialNumberDescription OBJECT-TYPE
    SYNTAX        DisplayString (SIZE(0..63))
    MAX-ACCESS    read-only
    STATUS        current
    DESCRIPTION
        "Component which this serial number entry maps to."
    ::= { cdcp4220SerialNumberEntry 2 }

cdcp4220SerialNumberVersion OBJECT-TYPE
    SYNTAX        DisplayString (SIZE(0..63))
    MAX-ACCESS    read-only
    STATUS        current
    DESCRIPTION
        "The serial number of the component this row represents. ."
    ::= { cdcp4220SerialNumberEntry 3 }

cdcp4220Priv OBJECT IDENTIFIER ::= { cdcp4220Config 3 }

cdcp4220CertificateIcp OBJECT-TYPE
    SYNTAX        X509Certificate
    MAX-ACCESS    read-only
    STATUS        current
    DESCRIPTION
        "This object contains the Interface Certificate.  The object
         value must be the ASN.1 DER encoding of the MTA manufacturer's
         X.509 public key certificate. ,contains the MTA's MAC  address.
         It The MTA Manufacturer Certificate is issued to each MTA
         manufacturer and is installed into each MTA at the time of
         manufacture or with a secure code download. The specific
         requirements related to this certificate are defined in  the
         Security specification."
    REFERENCE
        "Security Specification."
    ::= { cdcp4220Priv 1 }

cdcp4220CertificateLD OBJECT-TYPE
    SYNTAX        X509Certificate
    MAX-ACCESS    read-only
    STATUS        current
    DESCRIPTION
        "ASN.1 DER encoding of the MTA's X.509 public-key  certificate
         issued by the manufacturer and installed  into the embedded-MTA
         in the factory. This certificate,  called Certificate, cannot
         be updated by the provisioning server."
    ::= { cdcp4220Priv 2 }

cdcp4220IcpType OBJECT-TYPE
    SYNTAX        INTEGER {
        -- Unknown
        na(1),
        -- 8 MegaByte flash
        series2mb8(2),
        -- 16 MegaByte flash
        series2mb16(3),
	-- ICP 1.5 - 16 MegaByte flash
	series2Icp15mb16(4)
    }
    MAX-ACCESS    read-only
    STATUS        current
    DESCRIPTION
        "Returns the ICP type:
         Series2 - 8 MB flash 
         Series2 - 16 MB flash
         Series2 - ICP 1.5 - 16 MB flash"
    ::= { cdcp4220Config 4 }

cdcp4220DmdType OBJECT-TYPE
    SYNTAX        INTEGER {
        -- Not attached or unknown
        na(1),
        -- .98 inch DMD
        dc2k98(2),
        -- 2k 1.2 inch DMD
        dc2k12(3),
        -- 4k 1.38 inch DMD
        dc4k138(4)
    }
    MAX-ACCESS    read-only
    STATUS        current
    DESCRIPTION
        "Returns the DMD Type:
         2K - 0.98 inch DMD
         2K - 1.2 inch DMD
         4K - 1.38 inch DMD"
    ::= { cdcp4220Config 5 }

cdcp4220SatelliteType OBJECT IDENTIFIER ::= { cdcp4220Config 6 }

cdcp4220RedSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4220SatelliteType 1 }

cdcp4220GreenSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4220SatelliteType 2 }

cdcp4220BlueSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4220SatelliteType 3 }

cdcp4220Peripherals OBJECT IDENTIFIER ::= { cdcp4220Config 7 }

cdcp4220IlsInstalled OBJECT-TYPE
    SYNTAX        TruthValue
    MAX-ACCESS    read-only
    STATUS        current
    DESCRIPTION
        "Returns true if ILS is installed otherwise returns false."
    ::= { cdcp4220Peripherals 1 }

cdcp4220LdInstalled OBJECT-TYPE
    SYNTAX        TruthValue
    MAX-ACCESS    read-only
    STATUS        current
    DESCRIPTION
        "Returns true if LD is installed otherwise returns false."
    ::= { cdcp4220Peripherals 2 }

cdcp4220MediaBlockInstalled OBJECT-TYPE
    SYNTAX        TruthValue
    MAX-ACCESS    read-only
    STATUS        current
    DESCRIPTION
        "Returns true if MediaBlock is installed otherwise returns
         false."
    ::= { cdcp4220Peripherals 3 }

cdcp4220Status OBJECT IDENTIFIER ::= { cp4220 2 }

-- ====================================================================
-- 
-- Security status group

cdcp4220SecurityStatus OBJECT IDENTIFIER ::= { cdcp4220Status 1 }

cdcp4220SecurityArmed OBJECT-TYPE
    SYNTAX        INTEGER {
        armed(1),
        notArmed(2),
        na(3)
    }
    MAX-ACCESS    read-only
    STATUS        current
    DESCRIPTION
        "Security enclosure armed."
    ::= { cdcp4220SecurityStatus 1 }

cdcp4220SecurityTamper OBJECT-TYPE
    SYNTAX        INTEGER {
        tamper(1),
        secure(2),
        na(3)
    }
    MAX-ACCESS    read-only
    STATUS        current
    DESCRIPTION
        "Security enclosure tamper."
    ::= { cdcp4220SecurityStatus 2 }

cdcp4220MarriageActive OBJECT-TYPE
    SYNTAX        INTEGER {
        married(1),
        marriageBroken(2),
        na(3)
    }
    MAX-ACCESS    read-only
    STATUS        current
    DESCRIPTION
        "Marriage State,  When marriage is broken, no encrypted content
         can be played."
    ::= { cdcp4220SecurityStatus 3 }

cdcp4220PhysicalMarriageTamper OBJECT-TYPE
    SYNTAX        INTEGER {
        tampered(1),
        secure(2),
        na(3)
    }
    MAX-ACCESS    read-only
    STATUS        current
    DESCRIPTION
        "Physical Marriage State, Removal of any board within the card
         cage will cause a Physical tamper."
    ::= { cdcp4220SecurityStatus 4 }

cdcp4220LogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the LD board or Image Media Block."
    ::= { cdcp4220SecurityStatus 5 }

cdcp4220SoftwareCertZeroization OBJECT-TYPE
    SYNTAX        INTEGER {
        zeroed(1),
        ok(2),
        na(3)
    }
    MAX-ACCESS    read-only
    STATUS        current
    DESCRIPTION
        "Certificate State, A zeroed certificate state indicates  that
         a tamper has occurred on the LD board."
    ::= { cdcp4220SecurityStatus 6 }

cdcp4220ServiceDoorTamper OBJECT-TYPE
    SYNTAX        INTEGER {
        tamper(1),
        secure(2),
        na(3)
    }
    MAX-ACCESS    read-only
    STATUS        current
    DESCRIPTION
        "Service door to light engine compartment"
    ::= { cdcp4220SecurityStatus 7 }

cdcp4220TopEnclosureOpen OBJECT-TYPE
    SYNTAX        INTEGER {
        tamper(1),
        secure(2),
        na(3)
    }
    MAX-ACCESS    read-only
    STATUS        current
    DESCRIPTION
        "Security enclosure state, top side."
    ::= { cdcp4220SecurityStatus 8 }

cdcp4220BottomEnclosureOpen OBJECT-TYPE
    SYNTAX        INTEGER {
        tamper(1),
        secure(2),
        na(3)
    }
    MAX-ACCESS    read-only
    STATUS        current
    DESCRIPTION
        "Security enclosure state, top side."
    ::= { cdcp4220SecurityStatus 9 }

cdcp4220SecurityBatteryEvent OBJECT-TYPE
    SYNTAX        INTEGER {
        failed(1),
        ok(2),
        na(3)
    }
    MAX-ACCESS    read-only
    STATUS        current
    DESCRIPTION
        "Battery failed"
    ::= { cdcp4220SecurityStatus 10 }

cdcp4220BatteryLow OBJECT-TYPE
    SYNTAX        INTEGER {
        low(1),
        ok(2),
        na(3)
    }
    MAX-ACCESS    read-only
    STATUS        current
    DESCRIPTION
        "Battery state."
    ::= { cdcp4220SecurityStatus 11 }

cdcp4220SecurityLog OBJECT-TYPE
    SYNTAX        INTEGER {
        ok(1),
        warning(2),
        error(3),
        na(4)
    }
    MAX-ACCESS    read-only
    STATUS        current
    DESCRIPTION
        "The Security Log Warning indicates that there are  less than
         100 log entry locations available before  unread log entries
         will be overwritten.

         The Security Log Error indicates that there is no  more room to
         write log entries.

         When this warning/error is active, the Server needs  to extract
         the log data (via ASM/TLS session) from  the LD Security Log.
         Reads of the security log by any other entity/means will not
         impact this warning."
    ::= { cdcp4220SecurityStatus 12 }
    
cdcp4220IMBSecurityArmed OBJECT-TYPE
    SYNTAX        INTEGER {
        armed(1),
        notArmed(2),
        na(3)
    }
    MAX-ACCESS    read-only
    STATUS        current
    DESCRIPTION
        "IMB Security enclosure armed."
    ::= { cdcp4220SecurityStatus 13 }

cdcp4220IMBSecurityTamper OBJECT-TYPE
    SYNTAX        INTEGER {
        tamper(1),
        secure(2),
        na(3)
    }
    MAX-ACCESS    read-only
    STATUS        current
    DESCRIPTION
        "IMB Security enclosure tamper."
    ::= { cdcp4220SecurityStatus 14 }

cdcp4220IMBMarriageActive OBJECT-TYPE
    SYNTAX        INTEGER {
        married(1),
        marriageBroken(2),
        na(3)
    }
    MAX-ACCESS    read-only
    STATUS        current
    DESCRIPTION
        "IMB Marriage State,  When marriage is broken, no encrypted content
         can be played."
    ::= { cdcp4220SecurityStatus 15 }

cdcp4220IMBPhysicalMarriageTamper OBJECT-TYPE
    SYNTAX        INTEGER {
        tampered(1),
        secure(2),
        na(3)
    }
    MAX-ACCESS    read-only
    STATUS        current
    DESCRIPTION
        "IMB Physical Marriage State, Removal of any board within the card
         cage will cause a Physical tamper."
    ::= { cdcp4220SecurityStatus 16 }

cdcp4220IMBLogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the Image Media Block."
    ::= { cdcp4220SecurityStatus 17 }
    
cdcp4220IMBServiceDoorArmed OBJECT-TYPE
    SYNTAX        INTEGER {
        armed(1),
        tamper(2),
        na(3)
    }
    MAX-ACCESS    read-only
    STATUS        current
    DESCRIPTION
        "Service door to light engine compartment"
    ::= { cdcp4220SecurityStatus 18 }

cdcp4220IMBServiceDoorTamper OBJECT-TYPE
    SYNTAX        INTEGER {
        tamper(1),
        secure(2),
        na(3)
    }
    MAX-ACCESS    read-only
    STATUS        current
    DESCRIPTION
        "IMB Service door to light engine compartment"
    ::= { cdcp4220SecurityStatus 19 }

cdcp4220IMBBatteryLow OBJECT-TYPE
    SYNTAX        INTEGER {
        low(1),
        ok(2),
        na(3)
    }
    MAX-ACCESS    read-only
    STATUS        current
    DESCRIPTION
        "IMB Battery state."
    ::= { cdcp4220SecurityStatus 20 }
    
cdcp4220IMBICPCommunicationError OBJECT-TYPE
    SYNTAX        INTEGER {
        error(1),
        ok(2),
        na(3)
    }
    MAX-ACCESS    read-only
    STATUS        current
    DESCRIPTION
        "IMB Battery state."
    ::= { cdcp4220SecurityStatus 21 }

-- ====================================================================
-- 
-- Sensor tables

cdcp4220Sensors OBJECT IDENTIFIER ::= { cdcp4220Status 2 }

cdcp4220TempSensorsTable OBJECT-TYPE
    SYNTAX        SEQUENCE OF Cdcp4220TempSensorsEntry
    MAX-ACCESS    not-accessible
    STATUS        current
    DESCRIPTION
        "Table of temperature sensors and their values."
    ::= { cdcp4220Sensors 1 }

cdcp4220TempSensorsEntry OBJECT-TYPE
    SYNTAX        Cdcp4220TempSensorsEntry
    MAX-ACCESS    not-accessible
    STATUS        current
    DESCRIPTION
        "An entry containing a device and its statistics."
    INDEX
        { cdcp4220TempSensorsIndex }
    ::= { cdcp4220TempSensorsTable 1 }

Cdcp4220TempSensorsEntry ::= SEQUENCE
{
    cdcp4220TempSensorsIndex      Integer32,
    cdcp4220TempSensorsDevice     DisplayString,
    cdcp4220TempSensorsDiodeError TruthValue,
    cdcp4220TempSensorsLowerLimit TruthValue,
    cdcp4220TempSensorsUpperLimit TruthValue,
    cdcp4220TempSensorsValue      Gauge32
}

cdcp4220TempSensorsIndex OBJECT-TYPE
    SYNTAX        Integer32 (0..65535)
    MAX-ACCESS    read-only
    STATUS        current
    DESCRIPTION
        "Reference index for each observed device."
    ::= { cdcp4220TempSensorsEntry 1 }

cdcp4220TempSensorsDevice OBJECT-TYPE
    SYNTAX        DisplayString (SIZE(0..63))
    MAX-ACCESS    read-only
    STATUS        current
    DESCRIPTION
        "The name of the temperature sensor we are reading."
    ::= { cdcp4220TempSensorsEntry 2 }

cdcp4220TempSensorsDiodeError OBJECT-TYPE
    SYNTAX        TruthValue
    MAX-ACCESS    read-only
    STATUS        current
    DESCRIPTION
        "True if a diode error has occurred."
    ::= { cdcp4220TempSensorsEntry 3 }

cdcp4220TempSensorsLowerLimit OBJECT-TYPE
    SYNTAX        TruthValue
    MAX-ACCESS    read-only
    STATUS        current
    DESCRIPTION
        "True if the sensor has breached it's lower limit."
    ::= { cdcp4220TempSensorsEntry 4 }

cdcp4220TempSensorsUpperLimit OBJECT-TYPE
    SYNTAX        TruthValue
    MAX-ACCESS    read-only
    STATUS        current
    DESCRIPTION
        "True if the sensor has breached it's upper limit."
    ::= { cdcp4220TempSensorsEntry 5 }

cdcp4220TempSensorsValue OBJECT-TYPE
    SYNTAX        Gauge32
    MAX-ACCESS    read-only
    STATUS        current
    DESCRIPTION
        "The temperature of this sensor in Celsius"
    ::= { cdcp4220TempSensorsEntry 6 }

cdcp4220FanSensorsTable OBJECT-TYPE
    SYNTAX        SEQUENCE OF Cdcp4220FanSensorsEntry
    MAX-ACCESS    not-accessible
    STATUS        current
    DESCRIPTION
        "Table of fan sensors and their values."
    ::= { cdcp4220Sensors 2 }

cdcp4220FanSensorsEntry OBJECT-TYPE
    SYNTAX        Cdcp4220FanSensorsEntry
    MAX-ACCESS    not-accessible
    STATUS        current
    DESCRIPTION
        "An entry containing a device and its statistics."
    INDEX
        { cdcp4220FanSensorsIndex }
    ::= { cdcp4220FanSensorsTable 1 }

Cdcp4220FanSensorsEntry ::= SEQUENCE
{
    cdcp4220FanSensorsIndex   Integer32,
    cdcp4220FanSensorsDevice  DisplayString,
    cdcp4220FanSensorsFault   TruthValue,
    cdcp4220FanSensorsTooSlow TruthValue,
    cdcp4220FanSensorsValue   Gauge32
}

cdcp4220FanSensorsIndex OBJECT-TYPE
    SYNTAX        Integer32 (0..65535)
    MAX-ACCESS    read-only
    STATUS        current
    DESCRIPTION
        "Reference index for each observed device."
    ::= { cdcp4220FanSensorsEntry 1 }

cdcp4220FanSensorsDevice OBJECT-TYPE
    SYNTAX        DisplayString (SIZE(0..63))
    MAX-ACCESS    read-only
    STATUS        current
    DESCRIPTION
        "The name of the fan sensor we are reading."
    ::= { cdcp4220FanSensorsEntry 2 }

cdcp4220FanSensorsFault OBJECT-TYPE
    SYNTAX        TruthValue
    MAX-ACCESS    read-only
    STATUS        current
    DESCRIPTION
        "True if the fan has faulted."
    ::= { cdcp4220FanSensorsEntry 3 }

cdcp4220FanSensorsTooSlow OBJECT-TYPE
    SYNTAX        TruthValue
    MAX-ACCESS    read-only
    STATUS        current
    DESCRIPTION
        "True if a fan speed error has occurred with this fan."
    ::= { cdcp4220FanSensorsEntry 4 }

cdcp4220FanSensorsValue OBJECT-TYPE
    SYNTAX        Gauge32
    MAX-ACCESS    read-only
    STATUS        current
    DESCRIPTION
        "The rotation speed of the fan in RPM."
    ::= { cdcp4220FanSensorsEntry 5 }

cdcp4220InterlockSensorsTable OBJECT-TYPE
    SYNTAX        SEQUENCE OF Cdcp4220InterlockSensorsEntry
    MAX-ACCESS    not-accessible
    STATUS        current
    DESCRIPTION
        "Table of interlock sensors and their value."
    ::= { cdcp4220Sensors 3 }

cdcp4220InterlockSensorsEntry OBJECT-TYPE
    SYNTAX        Cdcp4220InterlockSensorsEntry
    MAX-ACCESS    not-accessible
    STATUS        current
    DESCRIPTION
        "An entry containing a device and its statistics."
    INDEX
        { cdcp4220InterlockSensorsIndex }
    ::= { cdcp4220InterlockSensorsTable 1 }

Cdcp4220InterlockSensorsEntry ::= SEQUENCE
{
    cdcp4220InterlockSensorsIndex  Integer32,
    cdcp4220InterlockSensorsDevice DisplayString,
    cdcp4220InterlockSensorsValue  INTEGER
}

cdcp4220InterlockSensorsIndex OBJECT-TYPE
    SYNTAX        Integer32 (0..65535)
    MAX-ACCESS    read-only
    STATUS        current
    DESCRIPTION
        "Reference index for each observed device."
    ::= { cdcp4220InterlockSensorsEntry 1 }

cdcp4220InterlockSensorsDevice OBJECT-TYPE
    SYNTAX        DisplayString (SIZE(0..63))
    MAX-ACCESS    read-only
    STATUS        current
    DESCRIPTION
        "The name of the interlock sensor we are reading."
    ::= { cdcp4220InterlockSensorsEntry 2 }

cdcp4220InterlockSensorsValue OBJECT-TYPE
    SYNTAX        INTEGER {
        open(1),
        closed(2),
        troubleOpen(3),
        troubleClosed(4)
    }
    MAX-ACCESS    read-only
    STATUS        current
    DESCRIPTION
        "The status of this interlock."
    ::= { cdcp4220InterlockSensorsEntry 3 }

-- ====================================================================
-- 
-- System health table, reports diagnostic test results.

cdcp4220SystemHealthTable OBJECT-TYPE
    SYNTAX        SEQUENCE OF Cdcp4220SystemHealthEntry
    MAX-ACCESS    not-accessible
    STATUS        current
    DESCRIPTION
        "Table of diagnostic tests and their results"
    ::= { cdcp4220Status 3 }

cdcp4220SystemHealthEntry OBJECT-TYPE
    SYNTAX        Cdcp4220SystemHealthEntry
    MAX-ACCESS    not-accessible
    STATUS        current
    DESCRIPTION
        "Each row respresents a diagnostic test and the result."
    INDEX
        { cdcp4220SystemHealthIndex }
    ::= { cdcp4220SystemHealthTable 1 }

Cdcp4220SystemHealthEntry ::= SEQUENCE
{
    cdcp4220SystemHealthIndex  Integer32,
    cdcp4220SystemHealthName   DisplayString,
    cdcp4220SystemHealthResult DisplayString
}

cdcp4220SystemHealthIndex OBJECT-TYPE
    SYNTAX        Integer32 (0..65535)
    MAX-ACCESS    read-only
    STATUS        current
    DESCRIPTION
        "Reference index for each observed test."
    ::= { cdcp4220SystemHealthEntry 1 }

cdcp4220SystemHealthName OBJECT-TYPE
    SYNTAX        DisplayString (SIZE(0..127))
    MAX-ACCESS    read-only
    STATUS        current
    DESCRIPTION
        "Name of the diagnostic being reported."
    ::= { cdcp4220SystemHealthEntry 2 }

cdcp4220SystemHealthResult OBJECT-TYPE
    SYNTAX        DisplayString (SIZE(0..127))
    MAX-ACCESS    read-only
    STATUS        current
    DESCRIPTION
        "Result of diagnostic."
    ::= { cdcp4220SystemHealthEntry 3 }

cdcp4220LensTable OBJECT-TYPE
    SYNTAX        SEQUENCE OF Cdcp4220LensEntry
    MAX-ACCESS    not-accessible
    STATUS        current
    DESCRIPTION
        "A table listing the lens entries."
    ::= { cdcp4220Status 4 }

cdcp4220LensEntry OBJECT-TYPE
    SYNTAX        Cdcp4220LensEntry
    MAX-ACCESS    not-accessible
    STATUS        current
    DESCRIPTION
        "The number of hours the projector has operated."
    INDEX
        { cdcp4220LensIdx }
    ::= { cdcp4220LensTable 1 }

Cdcp4220LensEntry ::= SEQUENCE
{
    cdcp4220LensIdx          Cdcp4220LensIndex,
    cdcp4220LensClass        DisplayString,
    cdcp4220LensType         DisplayString,
    cdcp4220LensSerialNumber DisplayString,
    cdcp4220LensStatus       INTEGER
}

cdcp4220LensIdx OBJECT-TYPE
    SYNTAX        Cdcp4220LensIndex (0..65535)
    MAX-ACCESS    read-only
    STATUS        current
    DESCRIPTION
        "Projector Lens index.  Each entry represents a various
         attributes of the Lens"
    ::= { cdcp4220LensEntry 1 }

cdcp4220LensClass OBJECT-TYPE
    SYNTAX        DisplayString (SIZE(0..255))
    MAX-ACCESS    read-only
    STATUS        current
    DESCRIPTION
        "Lens Class (Primary, Secondry...)"
    ::= { cdcp4220LensEntry 2 }

cdcp4220LensType OBJECT-TYPE
    SYNTAX        DisplayString (SIZE(0..255))
    MAX-ACCESS    read-only
    STATUS        current
    DESCRIPTION
        "Lens Type"
    ::= { cdcp4220LensEntry 3 }

cdcp4220LensSerialNumber OBJECT-TYPE
    SYNTAX        DisplayString (SIZE(0..255))
    MAX-ACCESS    read-only
    STATUS        current
    DESCRIPTION
        "Lens Serial Number"
    ::= { cdcp4220LensEntry 4 }

cdcp4220LensStatus OBJECT-TYPE
    SYNTAX        INTEGER {
        in(1),
        out(2)
    }
    MAX-ACCESS    read-only
    STATUS        current
    DESCRIPTION
        "Lens Status"
    ::= { cdcp4220LensEntry 5 }

cdcp4220System OBJECT IDENTIFIER ::= { cdcp4220Status 5 }

cdcp4220Tpc OBJECT IDENTIFIER ::= { cdcp4220System 1 }

cdcp4220TpcType OBJECT-TYPE
    SYNTAX        OCTET STRING
    MAX-ACCESS    read-only
    STATUS        current
    DESCRIPTION
        "Returns the TPC Type:
         TPC-660E TPC-650H"
    ::= { cdcp4220Tpc 1 }

cdcp4220TpcOs OBJECT-TYPE
    SYNTAX        OCTET STRING
    MAX-ACCESS    read-only
    STATUS        current
    DESCRIPTION
        "Returns the TPC OS Image"
    ::= { cdcp4220Tpc 2 }

cdcp4220TpcDiskSpaceAvailable OBJECT-TYPE
    SYNTAX        Integer32
    MAX-ACCESS    read-only
    STATUS        current
    DESCRIPTION
        "Returns the available TPC Disk Space"
    ::= { cdcp4220Tpc 3 }

cdcp4220TpcDiskSpaceUsed OBJECT-TYPE
    SYNTAX        Integer32
    MAX-ACCESS    read-only
    STATUS        current
    DESCRIPTION
        "Returns the TPC Disk Space, Used (MB)"
    ::= { cdcp4220Tpc 4 }

cdcp4220TpcMemorySpaceAvailable OBJECT-TYPE
    SYNTAX        Integer32
    MAX-ACCESS    read-only
    STATUS        current
    DESCRIPTION
        "Returns the available TPC Memory RAM (KB)"
    ::= { cdcp4220Tpc 5 }

cdcp4220Power OBJECT IDENTIFIER ::= { cdcp4220System 2 }

cdcp4220LvpsACok OBJECT-TYPE
    SYNTAX        INTEGER {
        -- OK
        yes(1),
        -- Fail
        no(2),
        -- Not available
        na(3)
    }
    MAX-ACCESS    read-only
    STATUS        current
    DESCRIPTION
        "Returns the AC OK signal state
         1 = yes
         2 = no
         3 = Not available"
    ::= { cdcp4220Power 1 }

cdcp4220LvpsDCok OBJECT-TYPE
    SYNTAX        INTEGER {
        -- OK
        yes(1),
        -- Fail
        no(2),
        -- Not available
        na(3)
    }
    MAX-ACCESS    read-only
    STATUS        current
    DESCRIPTION
        "Returns the CC OK signal state
         1 = yes
         2 = no
         3 = Not available"
    ::= { cdcp4220Power 2 }

cdcp4220PibPowerGoodVid OBJECT-TYPE
    SYNTAX        INTEGER {
        -- OK
        yes(1),
        -- Fail
        no(2),
        -- Not available
        na(3)
    }
    MAX-ACCESS    read-only
    STATUS        current
    DESCRIPTION
        "Returns the Power Good Vid signal state
         1 = yes
         2 = no
         3 = Not available"
    ::= { cdcp4220Power 3 }

cdcp4220PibPowerGood1v2and2v5 OBJECT-TYPE
    SYNTAX        INTEGER {
        -- OK
        yes(1),
        -- Fail
        no(2),
        -- Not available
        na(3)
    }
    MAX-ACCESS    read-only
    STATUS        current
    DESCRIPTION
        "Returns the PIB PowerGood signal for the 1.2v and 2.5v rails 1
         = yes
         2 = no
         3 = Not available"
    ::= { cdcp4220Power 4 }

cdcp4220PibPowerGood1v8and3v3 OBJECT-TYPE
    SYNTAX        INTEGER {
        -- OK
        yes(1),
        -- Fail
        no(2),
        -- Not available
        na(3)
    }
    MAX-ACCESS    read-only
    STATUS        current
    DESCRIPTION
        "Returns the PIB PowerGood signal for the 1.8v and 3.3v rails 1
         = yes
         2 = no
         3 = Not available"
    ::= { cdcp4220Power 5 }

cdcp4220PibPowerGood24vEXT OBJECT-TYPE
    SYNTAX        INTEGER {
        -- OK
        yes(1),
        -- Fail
        no(2),
        -- Not available
        na(3)
    }
    MAX-ACCESS    read-only
    STATUS        current
    DESCRIPTION
        "Returns the PIB PowerGood signal for the 24v External 1 = yes
         2 = no
         3 = Not available"
    ::= { cdcp4220Power 6 }

cdcp4220PibPowerGood24vSTBY OBJECT-TYPE
    SYNTAX        INTEGER {
        -- OK
        yes(1),
        -- Fail
        no(2),
        -- Not available
        na(3)
    }
    MAX-ACCESS    read-only
    STATUS        current
    DESCRIPTION
        "Returns the PIB PowerGood signal for the 24v Standby. 1 = yes
         2 = no
         3 = Not available"
    ::= { cdcp4220Power 7 }

cdcp4220Icp1v2 OBJECT-TYPE
    SYNTAX        OCTET STRING (SIZE(1..10))
    MAX-ACCESS    read-only
    STATUS        current
    DESCRIPTION
        "Returns the ICP 1.2v rail measurements or NA if in Standby"
    ::= { cdcp4220Power 8 }

cdcp4220Icp1v8 OBJECT-TYPE
    SYNTAX        OCTET STRING (SIZE(1..10))
    MAX-ACCESS    read-only
    STATUS        current
    DESCRIPTION
        "Returns the ICP 1.8v rail measurements or NA if in Standby"
    ::= { cdcp4220Power 9 }

cdcp4220Icp2v5 OBJECT-TYPE
    SYNTAX        OCTET STRING (SIZE(1..10))
    MAX-ACCESS    read-only
    STATUS        current
    DESCRIPTION
        "Returns the ICP 2.5v rail measurements or NA if in Standby"
    ::= { cdcp4220Power 10 }

cdcp4220Icp3v3 OBJECT-TYPE
    SYNTAX        OCTET STRING (SIZE(1..10))
    MAX-ACCESS    read-only
    STATUS        current
    DESCRIPTION
        "Returns the ICP 3.3v rail measurements or NA if in Standby"
    ::= { cdcp4220Power 11 }

cdcp4220IcpCommunicating OBJECT-TYPE
    SYNTAX        TruthValue
    MAX-ACCESS    read-only
    STATUS        current
    DESCRIPTION
        "Returns IPC State:
         True = Communicating False = Not Communicating"
    ::= { cdcp4220System 3 }

cdcp4220LinkDecryptor OBJECT IDENTIFIER ::= { cdcp4220System 4 }

cdcp4220LdCommunicating OBJECT-TYPE
    SYNTAX        TruthValue
    MAX-ACCESS    read-only
    STATUS        current
    DESCRIPTION
        "Returns the ICP connection state.
         True = Communicating False = Not Communicating"
    ::= { cdcp4220LinkDecryptor 1 }

cdcp4220LdLink0 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link states:
         No Source Decryption Not Active Decryption Active Decryption
         Error Unknown"
    ::= { cdcp4220LinkDecryptor 2 }

cdcp4220LdLink1 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link1 states:
         No Source Decryption Not Active Decryption Active Decryption
         Error Unknown"
    ::= { cdcp4220LinkDecryptor 3 }

cdcp4220LdLink2 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link2 states:
         No Source Decryption Not Active Decryption Active Decryption
         Error Unknown"
    ::= { cdcp4220LinkDecryptor 4 }

cdcp4220LdLink3 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link3 states:
         No Source Decryption Not Active Decryption Active Decryption
         Error Unknown"
    ::= { cdcp4220LinkDecryptor 5 }
    
cdcp4220Icp OBJECT-IDENTITY
    STATUS        current
    DESCRIPTION
        "ICP related objects"
    ::= { cdcp4220System 5 }

cdcp4220IcpDiskSpaceTotal OBJECT-TYPE
    SYNTAX        Integer32
    MAX-ACCESS    read-only
    STATUS        current
    DESCRIPTION
        "Returns the available ICP Disk Space (KB)"
    ::= { cdcp4220Icp 1 }

cdcp4220IcpDiskSpaceFree OBJECT-TYPE
    SYNTAX        Integer32
    MAX-ACCESS    read-only
    STATUS        current
    DESCRIPTION
        "Returns the ICP Disk Space, Free (KB)"
    ::= { cdcp4220Icp 2 }

cdcp4220StatusPeripherals OBJECT IDENTIFIER ::= { cdcp4220Status 6 }
    

END
