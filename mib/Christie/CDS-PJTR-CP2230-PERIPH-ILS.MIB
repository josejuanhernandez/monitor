CDS-PJTR-CP2230-PERIPH-ILS DEFINITIONS ::= BEGIN

IMPORTS
    cdcp2230StatusPeripherals
        FROM CDS-PJTR-CP2230
    MODULE-COMPLIANCE, NOTIFICATION-GROUP, OBJECT-GROUP
        FROM SNMPv2-CONF
    MODULE-IDENTITY, NOTIFICATION-TYPE, OBJECT-IDENTITY, OBJECT-TYPE
        FROM SNMPv2-SMI
    TEXTUAL-CONVENTION
        FROM SNMPv2-TC
    ;

cdcp2230PeriphIls MODULE-IDENTITY
    LAST-UPDATED  "201008111814Z" -- August 11, 2010
    ORGANIZATION
        "Christie Digital Systems, Inc."
    CONTACT-INFO
        "Christie Digital Systems
         Customer Service

         Postal:     10550 Camden Drive
         Cypress, Ca 90630
         USA

         Tel:        +1 800 221-8025

         E-mail:     support@christiedigital.com"
    DESCRIPTION
        "The MIB module for CDS Entertainment Solutions CP2230 Cinema
         projector.
         iso(1).org(3).dod(6).internet(1).private(4).enterprises(1)
         .christiedigital(25766)
         .christieDigitalProduct(1)
         .cdEs(12).cdEsProjector(3)"
    ::= { cdcp2230StatusPeripherals 1 }

cdcp2230PeriphIlsNotifications OBJECT IDENTIFIER ::= { cdcp2230StatusPeripherals 0 }

cdcp2230PeriphIlsObjects OBJECT IDENTIFIER ::= { cdcp2230PeriphIls 1 }

cdcp2230PeriphIlsStats OBJECT IDENTIFIER ::= { cdcp2230PeriphIlsObjects 1 }

cdcp2230PeriphIlsCommunicating OBJECT-TYPE
    SYNTAX        INTEGER {
        yes(1),
        no(2),
        na(3)
    }
    MAX-ACCESS    read-only
    STATUS        current
    DESCRIPTION
        "Returns:
         yes, if ILS board is communicating no, if ILS board is
         communicating na, if board not installed"
    ::= { cdcp2230PeriphIlsStats 1 }

cdcp2230PeriphIlsBoardID OBJECT-TYPE
    SYNTAX        OCTET STRING (SIZE(0..20))
    MAX-ACCESS    read-only
    STATUS        current
    DESCRIPTION
        "Returns the Electronic board ID"
    ::= { cdcp2230PeriphIlsStats 2 }

cdcp2230PeriphIlsVersions OBJECT IDENTIFIER ::= { cdcp2230PeriphIlsStats 3 }

cdcp2230PeriphIlsBootVersion OBJECT-TYPE
    SYNTAX        OCTET STRING (SIZE(0..20))
    MAX-ACCESS    read-only
    STATUS        current
    DESCRIPTION
        "Returns the Boot Loader version"
    ::= { cdcp2230PeriphIlsVersions 1 }

cdcp2230PeriphIlsMainVersion OBJECT-TYPE
    SYNTAX        OCTET STRING (SIZE(0..20))
    MAX-ACCESS    read-only
    STATUS        current
    DESCRIPTION
        "Returns the Main Software version"
    ::= { cdcp2230PeriphIlsVersions 2 }

cdcp2230PeriphIlsHwVersion OBJECT-TYPE
    SYNTAX        OCTET STRING (SIZE(0..20))
    MAX-ACCESS    read-only
    STATUS        current
    DESCRIPTION
        "Returns the Hardware version"
    ::= { cdcp2230PeriphIlsVersions 3 }

cdcp2230PeriphIlsTemperature OBJECT-TYPE
    SYNTAX        INTEGER (-999..200)
    MAX-ACCESS    read-only
    STATUS        current
    DESCRIPTION
        "Returns the onboard temperature (or -999 if not avaliable)"
    ::= { cdcp2230PeriphIlsStats 4 }

cdcp2230PeriphIlsMainCrcOK OBJECT-TYPE
    SYNTAX        INTEGER {
        yes(1),
        no(2),
        na(3)
    }
    MAX-ACCESS    read-only
    STATUS        current
    DESCRIPTION
        "Returns:
         yes, if Main software CRC is OK. no, if Main software CRC is
         not OK. na, if board not installed or not communicating"
    ::= { cdcp2230PeriphIlsStats 5 }

cdcp2230PeriphIlsSensors OBJECT IDENTIFIER ::= { cdcp2230PeriphIlsStats 6 }

cdcp2230PeriphIlsXSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp2230PeriphIlsSensors 1 }

cdcp2230PeriphIlsYSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp2230PeriphIlsSensors 2 }

cdcp2230PeriphIlsZoomSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp2230PeriphIlsSensors 3 }

cdcp2230PeriphIlsFocusSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp2230PeriphIlsSensors 4 }

cdcp2230PeriphIlsConfig OBJECT IDENTIFIER ::= { cdcp2230PeriphIlsObjects 3 }

cdcp2230PeriphIlsAutoEnabled OBJECT-TYPE
    SYNTAX        INTEGER {
        yes(1),
        no(2),
        na(3)
    }
    MAX-ACCESS    read-only
    STATUS        current
    DESCRIPTION
        "Returns 'Auto ILS' is enable state."
    ::= { cdcp2230PeriphIlsConfig 1 }

cdcp2230PeriphIlsResetOnStartup OBJECT-TYPE
    SYNTAX        INTEGER {
        yes(1),
        no(2),
        na(3)
    }
    MAX-ACCESS    read-only
    STATUS        current
    DESCRIPTION
        "Returns ILS 'Reset on Startup' state."
    ::= { cdcp2230PeriphIlsConfig 2 }

cdcp2230PeriphIlsResetOnBrownOut OBJECT-TYPE
    SYNTAX        INTEGER {
        yes(1),
        no(2),
        na(3)
    }
    MAX-ACCESS    read-only
    STATUS        current
    DESCRIPTION
        "Returns ILS 'Reset on Brown Out' state."
    ::= { cdcp2230PeriphIlsConfig 3 }

cdcp2230PeriphIlsConformance OBJECT IDENTIFIER ::= { cdcp2230PeriphIls 2 }

cdcp2230PeriphIlsCompliances OBJECT IDENTIFIER ::= { cdcp2230PeriphIlsConformance 1 }

cdcp2230PeriphIlsGroups OBJECT IDENTIFIER ::= { cdcp2230PeriphIlsConformance 2 }

cdcp2230PeriphIlsGroupAll OBJECT-GROUP
    OBJECTS
        { cdcp2230PeriphIlsBoardID, cdcp2230PeriphIlsCommunicating,
        cdcp2230PeriphIlsBootVersion, cdcp2230PeriphIlsMainVersion,
        cdcp2230PeriphIlsHwVersion, cdcp2230PeriphIlsTemperature,
        cdcp2230PeriphIlsMainCrcOK, cdcp2230PeriphIlsXSensorOK,
        cdcp2230PeriphIlsYSensorOK, cdcp2230PeriphIlsZoomSensorOK,
        cdcp2230PeriphIlsFocusSensorOK, cdcp2230PeriphIlsAutoEnabled,
        cdcp2230PeriphIlsResetOnStartup, cdcp2230PeriphIlsResetOnBrownOut }
    STATUS        current
    DESCRIPTION
        "Group of objects implemented in the projector peripherals (ILS
         option) for reporting the status of ILS."
    ::= { cdcp2230PeriphIlsGroups 1 }

END
