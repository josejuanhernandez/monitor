CDS-PJTR-CP2208-NOTIFY DEFINITIONS ::= BEGIN

IMPORTS
    cp2208
        FROM CDS-PJTR-CP2208
    NOTIFICATION-GROUP, OBJECT-GROUP
        FROM SNMPv2-CONF
    MODULE-IDENTITY, NOTIFICATION-TYPE, OBJECT-TYPE
        FROM SNMPv2-SMI
    DisplayString
        FROM SNMPv2-TC
    ;

cdcp2208Notification MODULE-IDENTITY
    LAST-UPDATED  "201212191650Z" -- December 19, 2012
    ORGANIZATION
        "Christie Digital Systems, Inc."
    CONTACT-INFO
        "Christie Digital Systems
         Customer Service

         Postal:  10550 Camden Drive
         Cypress, Ca 90630
         USA

         Tel:  +1 800 221-8025

         E-mail:  support@cds.com"
    DESCRIPTION
        "The MIB module for CDS cinema projector notifications. Alarms
         correspond to those generated within the TPC  and are
         documented in the manual."
    REVISION      "201212191650Z" -- December 19, 2012
    DESCRIPTION
        "Replaced LampLifeRotation with the LampHalfLife notification."

    ::= { cp2208 100 }

cdcp2208NotificationGroups OBJECT IDENTIFIER ::= { cdcp2208Notification 1 }

-- ====================================================================
-- 
-- Object groups

cdcp2208NotificationObjectsGroup OBJECT-GROUP
    OBJECTS
        { cdSensorName, cdSensorValue, cdComponentName, cdLampHours,
        cdTamperName, cdTamperValue }
    STATUS        current
    DESCRIPTION
        "Notification objects"
    ::= { cdcp2208NotificationGroups 1 }

-- cdcp2208NotificationGroup OBJECT-GROUP OBJECTS

cdcp2208NotificationGroup NOTIFICATION-GROUP
    NOTIFICATIONS
        { cdcp2208NotifyFan, cdcp2208NotifyInterlock,
        cdcp2208NotifyTemperature, cdcp2208NotifySystemComm,
        cdcp2208NotifyLampExpire, cdcp2208NotifyLampStrike,
        cdcp2208NotifyLampUnexpectedOff, cdcp2208NotifySecurityTamper,
        cdcp2208NotifyLampHalfLife, cdcp2208NotifyCoolant }
    STATUS        current
    DESCRIPTION
        "Notifications"
    ::= { cdcp2208NotificationGroups 2 }

cdcp2208NotificationObjects OBJECT IDENTIFIER ::= { cdcp2208Notification 2 }

-- ====================================================================
-- 
-- Notification objects

cdSensorName OBJECT-TYPE
    SYNTAX        DisplayString
    MAX-ACCESS    accessible-for-notify
    STATUS        current
    DESCRIPTION
        "Identifies the specific sensor which triggered the
         notification."
    ::= { cdcp2208NotificationObjects 1 }

cdSensorValue OBJECT-TYPE
    SYNTAX        DisplayString
    MAX-ACCESS    accessible-for-notify
    STATUS        current
    DESCRIPTION
        "A string with the formatted value of the sensor which
         triggered the notification."
    ::= { cdcp2208NotificationObjects 2 }

cdComponentName OBJECT-TYPE
    SYNTAX        DisplayString
    MAX-ACCESS    accessible-for-notify
    STATUS        current
    DESCRIPTION
        "Descripes the component which caused a comm error to trigger
         the notification."
    ::= { cdcp2208NotificationObjects 3 }

cdLampHours OBJECT-TYPE
    SYNTAX        INTEGER (0..65535)
    MAX-ACCESS    accessible-for-notify
    STATUS        current
    DESCRIPTION
        "Hours the installed lamp has operated."
    ::= { cdcp2208NotificationObjects 4 }

cdTamperName OBJECT-TYPE
    SYNTAX        DisplayString
    MAX-ACCESS    accessible-for-notify
    STATUS        current
    DESCRIPTION
        "Identifies the specific tamper which triggered the
         notification."
    ::= { cdcp2208NotificationObjects 5 }

cdTamperValue OBJECT-TYPE
    SYNTAX        DisplayString
    MAX-ACCESS    accessible-for-notify
    STATUS        current
    DESCRIPTION
        "A string with the formatted value of the tamper which
         triggered the notification."
    ::= { cdcp2208NotificationObjects 6 }

cdcp2208Notifications OBJECT IDENTIFIER ::= { cdcp2208Notification 3 }

cdcp2208NotificationsPrefix OBJECT IDENTIFIER ::= { cdcp2208Notifications 0 }

-- ====================================================================
-- 
-- Projector notifications

cdcp2208NotifyFan NOTIFICATION-TYPE
    OBJECTS
        { cdSensorName, cdSensorValue }
    STATUS        current
    DESCRIPTION
        "A fan speed error has occured."
    ::= { cdcp2208NotificationsPrefix 1 }

cdcp2208NotifyInterlock NOTIFICATION-TYPE
    OBJECTS
        { cdSensorName, cdSensorValue }
    STATUS        current
    DESCRIPTION
        "An interlock was tripped."
    ::= { cdcp2208NotificationsPrefix 2 }

cdcp2208NotifyTemperature NOTIFICATION-TYPE
    OBJECTS
        { cdSensorName, cdSensorValue }
    STATUS        current
    DESCRIPTION
        "Temperature sensor breached operational threshold."
    ::= { cdcp2208NotificationsPrefix 3 }

cdcp2208NotifySystemComm NOTIFICATION-TYPE
    OBJECTS
        { cdComponentName }
    STATUS        current
    DESCRIPTION
        "Communications to critical system component failed."
    ::= { cdcp2208NotificationsPrefix 4 }

cdcp2208NotifyLampExpire NOTIFICATION-TYPE
    OBJECTS
        { cdLampHours }
    STATUS        current
    DESCRIPTION
        "Lamp reached operational limit."
    ::= { cdcp2208NotificationsPrefix 5 }

cdcp2208NotifyLampStrike NOTIFICATION-TYPE
    OBJECTS
        { cdLampHours }
    STATUS        current
    DESCRIPTION
        "Lamp failed to strike."
    ::= { cdcp2208NotificationsPrefix 6 }

cdcp2208NotifyLampUnexpectedOff NOTIFICATION-TYPE
    OBJECTS
        { cdLampHours }
    STATUS        current
    DESCRIPTION
        "Unexpected lamp failure."
    ::= { cdcp2208NotificationsPrefix 7 }

cdcp2208NotifyCoolant NOTIFICATION-TYPE
    STATUS        current
    DESCRIPTION
        "Liquid cooling pump failure"
    ::= { cdcp2208NotificationsPrefix 8 }

cdcp2208NotifyLampHalfLife NOTIFICATION-TYPE
    OBJECTS
        { cdLampHours }
    STATUS        current
    DESCRIPTION
        "Lamp half life exceeded."
    ::= { cdcp2208NotificationsPrefix 9 }

cdcp2208NotifySecurityTamper NOTIFICATION-TYPE
    OBJECTS
        { cdTamperName, cdTamperValue }
    STATUS        current
    DESCRIPTION
        "Security System has been tampered tamper name and tamper
         state."
    ::= { cdcp2208NotificationsPrefix 10 }

END
