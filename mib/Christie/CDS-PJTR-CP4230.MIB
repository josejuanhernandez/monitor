CDS-PJTR-CP4230 DEFINITIONS ::= BEGIN

IMPORTS
    cdEsProjector
        FROM CDS-SMI
    Gauge32, Integer32, MODULE-IDENTITY, OBJECT-IDENTITY, OBJECT-TYPE
        FROM SNMPv2-SMI
    DisplayString, MacAddress, TEXTUAL-CONVENTION, TruthValue
        FROM SNMPv2-TC
    ;

cp4230 MODULE-IDENTITY
    LAST-UPDATED  "201008031914Z" -- August 03, 2010
    ORGANIZATION
        "Christie Digital Systems, Inc."
    CONTACT-INFO
        "Christie Digital Systems
         Customer Service

         Postal:     10550 Camden Drive
         Cypress, Ca 90630
         USA

         Tel:        +1 800 221-8025

         E-mail:     support@christiedigital.com"
    DESCRIPTION
        "The MIB module for CDS Entertainment Solutions CP4230 Cinema
         projector.
         iso(1).org(3).dod(6).internet(1).private(4).enterprises(1)
         .christiedigital(25766)
         .christieDigitalProduct(1)
         .cdEs(12).cdEsProjector(1)"
    REVISION      "201009141437Z" -- September 14, 2010
    DESCRIPTION
        "Added support for ICP Disk space"
    REVISION      "201008031933Z" -- August 03, 2010
    DESCRIPTION
	"First Revision"
    REVISION	  "201103301915Z" -- March 30, 2011
    DESCRIPTION
	"Updated: IcpType to include ICP 1.5 - 16 MegaByte Flash"        

    ::= { cdEsProjector 6 }

-- ====================================================================
-- 
-- Lens Table - a table of lens entries

Cdcp4230LensIndex ::= TEXTUAL-CONVENTION
    STATUS        current
    DESCRIPTION
        "A value used to index the Lens table."
    SYNTAX        Integer32

-- ====================================================================
-- 
-- Versions - a table of serial numbers of install sw/hw components

Cdcp4230SerialNumberIdx ::= TEXTUAL-CONVENTION
    STATUS        current
    DESCRIPTION
        "A value used to index projector serial numbers."
    SYNTAX        Integer32 (1..64)

-- ====================================================================
-- 
-- Versions - a table of versions of install sw/hw components

Cdcp4230VersionsIdx ::= TEXTUAL-CONVENTION
    STATUS        current
    DESCRIPTION
        "A value used to index projector versions."
    SYNTAX        Integer32 (1..64)

-- ====================================================================
-- 
-- Admin only

X509Certificate ::= TEXTUAL-CONVENTION
    STATUS        current
    DESCRIPTION
        "An X509 digital certificate encoded as an ASN.1 DER object."
    SYNTAX        OCTET STRING (SIZE(0..4096))

cdcp4230Config OBJECT IDENTIFIER ::= { cp4230 1 }

cdcp4230VersionsTable OBJECT-TYPE
    SYNTAX        SEQUENCE OF Cdcp4230VersionsEntry
    MAX-ACCESS    not-accessible
    STATUS        current
    DESCRIPTION
        "A table listing the versions of the projectors hardware and
         software components."
    ::= { cdcp4230Config 1 }

cdcp4230VersionsEntry OBJECT-TYPE
    SYNTAX        Cdcp4230VersionsEntry
    MAX-ACCESS    not-accessible
    STATUS        current
    DESCRIPTION
        "The projector component description and version."
    INDEX
        { cdcp4230VersionsIndex }
    ::= { cdcp4230VersionsTable 1 }

Cdcp4230VersionsEntry ::= SEQUENCE
{
    cdcp4230VersionsIndex       Cdcp4230VersionsIdx,
    cdcp4230VersionsDescription DisplayString,
    cdcp4230VersionsVersion     DisplayString
}

cdcp4230VersionsIndex OBJECT-TYPE
    SYNTAX        Cdcp4230VersionsIdx
    MAX-ACCESS    read-only
    STATUS        current
    DESCRIPTION
        "Projector Configuration index to which the parameters in this
         row apply."
    ::= { cdcp4230VersionsEntry 1 }

cdcp4230VersionsDescription OBJECT-TYPE
    SYNTAX        DisplayString (SIZE(0..63))
    MAX-ACCESS    read-only
    STATUS        current
    DESCRIPTION
        "Component which this version entry maps to."
    ::= { cdcp4230VersionsEntry 2 }

cdcp4230VersionsVersion OBJECT-TYPE
    SYNTAX        DisplayString (SIZE(0..63))
    MAX-ACCESS    read-only
    STATUS        current
    DESCRIPTION
        "The version or serial number of the component this row
         represents.
         ."
    ::= { cdcp4230VersionsEntry 3 }

cdcp4230SerialNumberTable OBJECT-TYPE
    SYNTAX        SEQUENCE OF Cdcp4230SerialNumberEntry
    MAX-ACCESS    not-accessible
    STATUS        current
    DESCRIPTION
        "A table listing the serial numbers of the projectors hardware
         and software components."
    ::= { cdcp4230Config 2 }

cdcp4230SerialNumberEntry OBJECT-TYPE
    SYNTAX        Cdcp4230SerialNumberEntry
    MAX-ACCESS    not-accessible
    STATUS        current
    DESCRIPTION
        "The projector component description and serial number."
    INDEX
        { cdcp4230SerialNumberIndex }
    ::= { cdcp4230SerialNumberTable 1 }

Cdcp4230SerialNumberEntry ::= SEQUENCE
{
    cdcp4230SerialNumberIndex       Cdcp4230SerialNumberIdx,
    cdcp4230SerialNumberDescription DisplayString,
    cdcp4230SerialNumberVersion     DisplayString
}

cdcp4230SerialNumberIndex OBJECT-TYPE
    SYNTAX        Cdcp4230SerialNumberIdx
    MAX-ACCESS    read-only
    STATUS        current
    DESCRIPTION
        "Projector Configuration index to which the parameters in this
         row apply."
    ::= { cdcp4230SerialNumberEntry 1 }

cdcp4230SerialNumberDescription OBJECT-TYPE
    SYNTAX        DisplayString (SIZE(0..63))
    MAX-ACCESS    read-only
    STATUS        current
    DESCRIPTION
        "Component which this serial number entry maps to."
    ::= { cdcp4230SerialNumberEntry 2 }

cdcp4230SerialNumberVersion OBJECT-TYPE
    SYNTAX        DisplayString (SIZE(0..63))
    MAX-ACCESS    read-only
    STATUS        current
    DESCRIPTION
        "The serial number of the component this row represents. ."
    ::= { cdcp4230SerialNumberEntry 3 }

cdcp4230Priv OBJECT IDENTIFIER ::= { cdcp4230Config 3 }

cdcp4230CertificateIcp OBJECT-TYPE
    SYNTAX        X509Certificate
    MAX-ACCESS    read-only
    STATUS        current
    DESCRIPTION
        "This object contains the Interface Certificate.  The object
         value must be the ASN.1 DER encoding of the MTA manufacturer's
         X.509 public key certificate. ,contains the MTA's MAC  address.
         It The MTA Manufacturer Certificate is issued to each MTA
         manufacturer and is installed into each MTA at the time of
         manufacture or with a secure code download. The specific
         requirements related to this certificate are defined in  the
         Security specification."
    REFERENCE
        "Security Specification."
    ::= { cdcp4230Priv 1 }

cdcp4230CertificateLD OBJECT-TYPE
    SYNTAX        X509Certificate
    MAX-ACCESS    read-only
    STATUS        current
    DESCRIPTION
        "ASN.1 DER encoding of the MTA's X.509 public-key  certificate
         issued by the manufacturer and installed  into the embedded-MTA
         in the factory. This certificate,  called Certificate, cannot
         be updated by the provisioning server."
    ::= { cdcp4230Priv 2 }

cdcp4230IcpType OBJECT-TYPE
    SYNTAX        INTEGER {
        -- Unknown
        na(1),
        -- 8 MegaByte flash
        series2mb8(2),
        -- 16 MegaByte flash
        series2mb16(3),
	-- ICP 1.5 - 16 MegaByte flash
	series2Icp15mb16(4)
    }
    MAX-ACCESS    read-only
    STATUS        current
    DESCRIPTION
        "Returns the ICP type:
         Series2 - 8 MB flash 
         Series2 - 16 MB flash
         Series2 - ICP 1.5 - 16 MB flash"
    ::= { cdcp4230Config 4 }

cdcp4230DmdType OBJECT-TYPE
    SYNTAX        INTEGER {
        -- Not attached or unknown
        na(1),
        -- .98 inch DMD
        dc2k98(2),
        -- 2k 1.2 inch DMD
        dc2k12(3),
        -- 4k 1.38 inch DMD
        dc4k138(4)
    }
    MAX-ACCESS    read-only
    STATUS        current
    DESCRIPTION
        "Returns the DMD Type:
         2K - 0.98 inch DMD
         2K - 1.2 inch DMD
         4K - 1.38 inch DMD"
    ::= { cdcp4230Config 5 }

cdcp4230SatelliteType OBJECT IDENTIFIER ::= { cdcp4230Config 6 }

cdcp4230RedSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4230SatelliteType 1 }

cdcp4230GreenSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4230SatelliteType 2 }

cdcp4230BlueSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4230SatelliteType 3 }

cdcp4230Peripherals OBJECT IDENTIFIER ::= { cdcp4230Config 7 }

cdcp4230IlsInstalled OBJECT-TYPE
    SYNTAX        TruthValue
    MAX-ACCESS    read-only
    STATUS        current
    DESCRIPTION
        "Returns true if ILS is installed otherwise returns false."
    ::= { cdcp4230Peripherals 1 }

cdcp4230LdInstalled OBJECT-TYPE
    SYNTAX        TruthValue
    MAX-ACCESS    read-only
    STATUS        current
    DESCRIPTION
        "Returns true if LD is installed otherwise returns false."
    ::= { cdcp4230Peripherals 2 }

cdcp4230MediaBlockInstalled OBJECT-TYPE
    SYNTAX        TruthValue
    MAX-ACCESS    read-only
    STATUS        current
    DESCRIPTION
        "Returns true if MediaBlock is installed otherwise returns
         false."
    ::= { cdcp4230Peripherals 3 }

cdcp4230Status OBJECT IDENTIFIER ::= { cp4230 2 }

-- ====================================================================
-- 
-- Security status group

cdcp4230SecurityStatus OBJECT IDENTIFIER ::= { cdcp4230Status 1 }

cdcp4230SecurityArmed OBJECT-TYPE
    SYNTAX        INTEGER {
        armed(1),
        notArmed(2),
        na(3)
    }
    MAX-ACCESS    read-only
    STATUS        current
    DESCRIPTION
        "Security enclosure armed."
    ::= { cdcp4230SecurityStatus 1 }

cdcp4230SecurityTamper OBJECT-TYPE
    SYNTAX        INTEGER {
        tamper(1),
        secure(2),
        na(3)
    }
    MAX-ACCESS    read-only
    STATUS        current
    DESCRIPTION
        "Security enclosure tamper."
    ::= { cdcp4230SecurityStatus 2 }

cdcp4230MarriageActive OBJECT-TYPE
    SYNTAX        INTEGER {
        married(1),
        marriageBroken(2),
        na(3)
    }
    MAX-ACCESS    read-only
    STATUS        current
    DESCRIPTION
        "Marriage State,  When marriage is broken, no encrypted content
         can be played."
    ::= { cdcp4230SecurityStatus 3 }

cdcp4230PhysicalMarriageTamper OBJECT-TYPE
    SYNTAX        INTEGER {
        tampered(1),
        secure(2),
        na(3)
    }
    MAX-ACCESS    read-only
    STATUS        current
    DESCRIPTION
        "Physical Marriage State, Removal of any board within the card
         cage will cause a Physical tamper."
    ::= { cdcp4230SecurityStatus 4 }

cdcp4230LogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the LD board or Image Media Block."
    ::= { cdcp4230SecurityStatus 5 }

cdcp4230SoftwareCertZeroization OBJECT-TYPE
    SYNTAX        INTEGER {
        zeroed(1),
        ok(2),
        na(3)
    }
    MAX-ACCESS    read-only
    STATUS        current
    DESCRIPTION
        "Certificate State, A zeroed certificate state indicates  that
         a tamper has occurred on the LD board."
    ::= { cdcp4230SecurityStatus 6 }

cdcp4230ServiceDoorTamper OBJECT-TYPE
    SYNTAX        INTEGER {
        tamper(1),
        secure(2),
        na(3)
    }
    MAX-ACCESS    read-only
    STATUS        current
    DESCRIPTION
        "Service door to light engine compartment"
    ::= { cdcp4230SecurityStatus 7 }

cdcp4230TopEnclosureOpen OBJECT-TYPE
    SYNTAX        INTEGER {
        tamper(1),
        secure(2),
        na(3)
    }
    MAX-ACCESS    read-only
    STATUS        current
    DESCRIPTION
        "Security enclosure state, top side."
    ::= { cdcp4230SecurityStatus 8 }

cdcp4230BottomEnclosureOpen OBJECT-TYPE
    SYNTAX        INTEGER {
        tamper(1),
        secure(2),
        na(3)
    }
    MAX-ACCESS    read-only
    STATUS        current
    DESCRIPTION
        "Security enclosure state, top side."
    ::= { cdcp4230SecurityStatus 9 }

cdcp4230SecurityBatteryEvent OBJECT-TYPE
    SYNTAX        INTEGER {
        failed(1),
        ok(2),
        na(3)
    }
    MAX-ACCESS    read-only
    STATUS        current
    DESCRIPTION
        "Battery failed"
    ::= { cdcp4230SecurityStatus 10 }

cdcp4230BatteryLow OBJECT-TYPE
    SYNTAX        INTEGER {
        low(1),
        ok(2),
        na(3)
    }
    MAX-ACCESS    read-only
    STATUS        current
    DESCRIPTION
        "Battery state."
    ::= { cdcp4230SecurityStatus 11 }

cdcp4230SecurityLog OBJECT-TYPE
    SYNTAX        INTEGER {
        ok(1),
        warning(2),
        error(3),
        na(4)
    }
    MAX-ACCESS    read-only
    STATUS        current
    DESCRIPTION
        "The Security Log Warning indicates that there are  less than
         100 log entry locations available before  unread log entries
         will be overwritten.

         The Security Log Error indicates that there is no  more room to
         write log entries.

         When this warning/error is active, the Server needs  to extract
         the log data (via ASM/TLS session) from  the LD Security Log.
         Reads of the security log by any other entity/means will not
         impact this warning."
    ::= { cdcp4230SecurityStatus 12 }
    
cdcp4230IMBSecurityArmed OBJECT-TYPE
    SYNTAX        INTEGER {
        armed(1),
        notArmed(2),
        na(3)
    }
    MAX-ACCESS    read-only
    STATUS        current
    DESCRIPTION
        "IMB Security enclosure armed."
    ::= { cdcp4230SecurityStatus 13 }

cdcp4230IMBSecurityTamper OBJECT-TYPE
    SYNTAX        INTEGER {
        tamper(1),
        secure(2),
        na(3)
    }
    MAX-ACCESS    read-only
    STATUS        current
    DESCRIPTION
        "IMB Security enclosure tamper."
    ::= { cdcp4230SecurityStatus 14 }

cdcp4230IMBMarriageActive OBJECT-TYPE
    SYNTAX        INTEGER {
        married(1),
        marriageBroken(2),
        na(3)
    }
    MAX-ACCESS    read-only
    STATUS        current
    DESCRIPTION
        "IMB Marriage State,  When marriage is broken, no encrypted content
         can be played."
    ::= { cdcp4230SecurityStatus 15 }

cdcp4230IMBPhysicalMarriageTamper OBJECT-TYPE
    SYNTAX        INTEGER {
        tampered(1),
        secure(2),
        na(3)
    }
    MAX-ACCESS    read-only
    STATUS        current
    DESCRIPTION
        "IMB Physical Marriage State, Removal of any board within the card
         cage will cause a Physical tamper."
    ::= { cdcp4230SecurityStatus 16 }

cdcp4230IMBLogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the Image Media Block."
    ::= { cdcp4230SecurityStatus 17 }
    
cdcp4230IMBServiceDoorArmed OBJECT-TYPE
    SYNTAX        INTEGER {
        armed(1),
        tamper(2),
        na(3)
    }
    MAX-ACCESS    read-only
    STATUS        current
    DESCRIPTION
        "Service door to light engine compartment"
    ::= { cdcp4230SecurityStatus 18 }

cdcp4230IMBServiceDoorTamper OBJECT-TYPE
    SYNTAX        INTEGER {
        tamper(1),
        secure(2),
        na(3)
    }
    MAX-ACCESS    read-only
    STATUS        current
    DESCRIPTION
        "IMB Service door to light engine compartment"
    ::= { cdcp4230SecurityStatus 19 }

cdcp4230IMBBatteryLow OBJECT-TYPE
    SYNTAX        INTEGER {
        low(1),
        ok(2),
        na(3)
    }
    MAX-ACCESS    read-only
    STATUS        current
    DESCRIPTION
        "IMB Battery state."
    ::= { cdcp4230SecurityStatus 20 }
    
cdcp4230IMBICPCommunicationError OBJECT-TYPE
    SYNTAX        INTEGER {
        error(1),
        ok(2),
        na(3)
    }
    MAX-ACCESS    read-only
    STATUS        current
    DESCRIPTION
        "IMB Battery state."
    ::= { cdcp4230SecurityStatus 21 }

-- ====================================================================
-- 
-- Sensor tables

cdcp4230Sensors OBJECT IDENTIFIER ::= { cdcp4230Status 2 }

cdcp4230TempSensorsTable OBJECT-TYPE
    SYNTAX        SEQUENCE OF Cdcp4230TempSensorsEntry
    MAX-ACCESS    not-accessible
    STATUS        current
    DESCRIPTION
        "Table of temperature sensors and their values."
    ::= { cdcp4230Sensors 1 }

cdcp4230TempSensorsEntry OBJECT-TYPE
    SYNTAX        Cdcp4230TempSensorsEntry
    MAX-ACCESS    not-accessible
    STATUS        current
    DESCRIPTION
        "An entry containing a device and its statistics."
    INDEX
        { cdcp4230TempSensorsIndex }
    ::= { cdcp4230TempSensorsTable 1 }

Cdcp4230TempSensorsEntry ::= SEQUENCE
{
    cdcp4230TempSensorsIndex      Integer32,
    cdcp4230TempSensorsDevice     DisplayString,
    cdcp4230TempSensorsDiodeError TruthValue,
    cdcp4230TempSensorsLowerLimit TruthValue,
    cdcp4230TempSensorsUpperLimit TruthValue,
    cdcp4230TempSensorsValue      Gauge32
}

cdcp4230TempSensorsIndex OBJECT-TYPE
    SYNTAX        Integer32 (0..65535)
    MAX-ACCESS    read-only
    STATUS        current
    DESCRIPTION
        "Reference index for each observed device."
    ::= { cdcp4230TempSensorsEntry 1 }

cdcp4230TempSensorsDevice OBJECT-TYPE
    SYNTAX        DisplayString (SIZE(0..63))
    MAX-ACCESS    read-only
    STATUS        current
    DESCRIPTION
        "The name of the temperature sensor we are reading."
    ::= { cdcp4230TempSensorsEntry 2 }

cdcp4230TempSensorsDiodeError OBJECT-TYPE
    SYNTAX        TruthValue
    MAX-ACCESS    read-only
    STATUS        current
    DESCRIPTION
        "True if a diode error has occurred."
    ::= { cdcp4230TempSensorsEntry 3 }

cdcp4230TempSensorsLowerLimit OBJECT-TYPE
    SYNTAX        TruthValue
    MAX-ACCESS    read-only
    STATUS        current
    DESCRIPTION
        "True if the sensor has breached it's lower limit."
    ::= { cdcp4230TempSensorsEntry 4 }

cdcp4230TempSensorsUpperLimit OBJECT-TYPE
    SYNTAX        TruthValue
    MAX-ACCESS    read-only
    STATUS        current
    DESCRIPTION
        "True if the sensor has breached it's upper limit."
    ::= { cdcp4230TempSensorsEntry 5 }

cdcp4230TempSensorsValue OBJECT-TYPE
    SYNTAX        Gauge32
    MAX-ACCESS    read-only
    STATUS        current
    DESCRIPTION
        "The temperature of this sensor in Celsius"
    ::= { cdcp4230TempSensorsEntry 6 }

cdcp4230FanSensorsTable OBJECT-TYPE
    SYNTAX        SEQUENCE OF Cdcp4230FanSensorsEntry
    MAX-ACCESS    not-accessible
    STATUS        current
    DESCRIPTION
        "Table of fan sensors and their values."
    ::= { cdcp4230Sensors 2 }

cdcp4230FanSensorsEntry OBJECT-TYPE
    SYNTAX        Cdcp4230FanSensorsEntry
    MAX-ACCESS    not-accessible
    STATUS        current
    DESCRIPTION
        "An entry containing a device and its statistics."
    INDEX
        { cdcp4230FanSensorsIndex }
    ::= { cdcp4230FanSensorsTable 1 }

Cdcp4230FanSensorsEntry ::= SEQUENCE
{
    cdcp4230FanSensorsIndex   Integer32,
    cdcp4230FanSensorsDevice  DisplayString,
    cdcp4230FanSensorsFault   TruthValue,
    cdcp4230FanSensorsTooSlow TruthValue,
    cdcp4230FanSensorsValue   Gauge32
}

cdcp4230FanSensorsIndex OBJECT-TYPE
    SYNTAX        Integer32 (0..65535)
    MAX-ACCESS    read-only
    STATUS        current
    DESCRIPTION
        "Reference index for each observed device."
    ::= { cdcp4230FanSensorsEntry 1 }

cdcp4230FanSensorsDevice OBJECT-TYPE
    SYNTAX        DisplayString (SIZE(0..63))
    MAX-ACCESS    read-only
    STATUS        current
    DESCRIPTION
        "The name of the fan sensor we are reading."
    ::= { cdcp4230FanSensorsEntry 2 }

cdcp4230FanSensorsFault OBJECT-TYPE
    SYNTAX        TruthValue
    MAX-ACCESS    read-only
    STATUS        current
    DESCRIPTION
        "True if the fan has faulted."
    ::= { cdcp4230FanSensorsEntry 3 }

cdcp4230FanSensorsTooSlow OBJECT-TYPE
    SYNTAX        TruthValue
    MAX-ACCESS    read-only
    STATUS        current
    DESCRIPTION
        "True if a fan speed error has occurred with this fan."
    ::= { cdcp4230FanSensorsEntry 4 }

cdcp4230FanSensorsValue OBJECT-TYPE
    SYNTAX        Gauge32
    MAX-ACCESS    read-only
    STATUS        current
    DESCRIPTION
        "The rotation speed of the fan in RPM."
    ::= { cdcp4230FanSensorsEntry 5 }

cdcp4230InterlockSensorsTable OBJECT-TYPE
    SYNTAX        SEQUENCE OF Cdcp4230InterlockSensorsEntry
    MAX-ACCESS    not-accessible
    STATUS        current
    DESCRIPTION
        "Table of interlock sensors and their value."
    ::= { cdcp4230Sensors 3 }

cdcp4230InterlockSensorsEntry OBJECT-TYPE
    SYNTAX        Cdcp4230InterlockSensorsEntry
    MAX-ACCESS    not-accessible
    STATUS        current
    DESCRIPTION
        "An entry containing a device and its statistics."
    INDEX
        { cdcp4230InterlockSensorsIndex }
    ::= { cdcp4230InterlockSensorsTable 1 }

Cdcp4230InterlockSensorsEntry ::= SEQUENCE
{
    cdcp4230InterlockSensorsIndex  Integer32,
    cdcp4230InterlockSensorsDevice DisplayString,
    cdcp4230InterlockSensorsValue  INTEGER
}

cdcp4230InterlockSensorsIndex OBJECT-TYPE
    SYNTAX        Integer32 (0..65535)
    MAX-ACCESS    read-only
    STATUS        current
    DESCRIPTION
        "Reference index for each observed device."
    ::= { cdcp4230InterlockSensorsEntry 1 }

cdcp4230InterlockSensorsDevice OBJECT-TYPE
    SYNTAX        DisplayString (SIZE(0..63))
    MAX-ACCESS    read-only
    STATUS        current
    DESCRIPTION
        "The name of the interlock sensor we are reading."
    ::= { cdcp4230InterlockSensorsEntry 2 }

cdcp4230InterlockSensorsValue OBJECT-TYPE
    SYNTAX        INTEGER {
        open(1),
        closed(2),
        troubleOpen(3),
        troubleClosed(4)
    }
    MAX-ACCESS    read-only
    STATUS        current
    DESCRIPTION
        "The status of this interlock."
    ::= { cdcp4230InterlockSensorsEntry 3 }

-- ====================================================================
-- 
-- System health table, reports diagnostic test results.

cdcp4230SystemHealthTable OBJECT-TYPE
    SYNTAX        SEQUENCE OF Cdcp4230SystemHealthEntry
    MAX-ACCESS    not-accessible
    STATUS        current
    DESCRIPTION
        "Table of diagnostic tests and their results"
    ::= { cdcp4230Status 3 }

cdcp4230SystemHealthEntry OBJECT-TYPE
    SYNTAX        Cdcp4230SystemHealthEntry
    MAX-ACCESS    not-accessible
    STATUS        current
    DESCRIPTION
        "Each row respresents a diagnostic test and the result."
    INDEX
        { cdcp4230SystemHealthIndex }
    ::= { cdcp4230SystemHealthTable 1 }

Cdcp4230SystemHealthEntry ::= SEQUENCE
{
    cdcp4230SystemHealthIndex  Integer32,
    cdcp4230SystemHealthName   DisplayString,
    cdcp4230SystemHealthResult DisplayString
}

cdcp4230SystemHealthIndex OBJECT-TYPE
    SYNTAX        Integer32 (0..65535)
    MAX-ACCESS    read-only
    STATUS        current
    DESCRIPTION
        "Reference index for each observed test."
    ::= { cdcp4230SystemHealthEntry 1 }

cdcp4230SystemHealthName OBJECT-TYPE
    SYNTAX        DisplayString (SIZE(0..127))
    MAX-ACCESS    read-only
    STATUS        current
    DESCRIPTION
        "Name of the diagnostic being reported."
    ::= { cdcp4230SystemHealthEntry 2 }

cdcp4230SystemHealthResult OBJECT-TYPE
    SYNTAX        DisplayString (SIZE(0..127))
    MAX-ACCESS    read-only
    STATUS        current
    DESCRIPTION
        "Result of diagnostic."
    ::= { cdcp4230SystemHealthEntry 3 }

cdcp4230LensTable OBJECT-TYPE
    SYNTAX        SEQUENCE OF Cdcp4230LensEntry
    MAX-ACCESS    not-accessible
    STATUS        current
    DESCRIPTION
        "A table listing the lens entries."
    ::= { cdcp4230Status 4 }

cdcp4230LensEntry OBJECT-TYPE
    SYNTAX        Cdcp4230LensEntry
    MAX-ACCESS    not-accessible
    STATUS        current
    DESCRIPTION
        "The number of hours the projector has operated."
    INDEX
        { cdcp4230LensIdx }
    ::= { cdcp4230LensTable 1 }

Cdcp4230LensEntry ::= SEQUENCE
{
    cdcp4230LensIdx          Cdcp4230LensIndex,
    cdcp4230LensClass        DisplayString,
    cdcp4230LensType         DisplayString,
    cdcp4230LensSerialNumber DisplayString,
    cdcp4230LensStatus       INTEGER
}

cdcp4230LensIdx OBJECT-TYPE
    SYNTAX        Cdcp4230LensIndex (0..65535)
    MAX-ACCESS    read-only
    STATUS        current
    DESCRIPTION
        "Projector Lens index.  Each entry represents a various
         attributes of the Lens"
    ::= { cdcp4230LensEntry 1 }

cdcp4230LensClass OBJECT-TYPE
    SYNTAX        DisplayString (SIZE(0..255))
    MAX-ACCESS    read-only
    STATUS        current
    DESCRIPTION
        "Lens Class (Primary, Secondry...)"
    ::= { cdcp4230LensEntry 2 }

cdcp4230LensType OBJECT-TYPE
    SYNTAX        DisplayString (SIZE(0..255))
    MAX-ACCESS    read-only
    STATUS        current
    DESCRIPTION
        "Lens Type"
    ::= { cdcp4230LensEntry 3 }

cdcp4230LensSerialNumber OBJECT-TYPE
    SYNTAX        DisplayString (SIZE(0..255))
    MAX-ACCESS    read-only
    STATUS        current
    DESCRIPTION
        "Lens Serial Number"
    ::= { cdcp4230LensEntry 4 }

cdcp4230LensStatus OBJECT-TYPE
    SYNTAX        INTEGER {
        in(1),
        out(2)
    }
    MAX-ACCESS    read-only
    STATUS        current
    DESCRIPTION
        "Lens Status"
    ::= { cdcp4230LensEntry 5 }

cdcp4230System OBJECT IDENTIFIER ::= { cdcp4230Status 5 }

cdcp4230Tpc OBJECT IDENTIFIER ::= { cdcp4230System 1 }

cdcp4230TpcType OBJECT-TYPE
    SYNTAX        OCTET STRING
    MAX-ACCESS    read-only
    STATUS        current
    DESCRIPTION
        "Returns the TPC Type:
         TPC-660E TPC-650H"
    ::= { cdcp4230Tpc 1 }

cdcp4230TpcOs OBJECT-TYPE
    SYNTAX        OCTET STRING
    MAX-ACCESS    read-only
    STATUS        current
    DESCRIPTION
        "Returns the TPC OS Image"
    ::= { cdcp4230Tpc 2 }

cdcp4230TpcDiskSpaceAvailable OBJECT-TYPE
    SYNTAX        Integer32
    MAX-ACCESS    read-only
    STATUS        current
    DESCRIPTION
        "Returns the available TPC Disk Space"
    ::= { cdcp4230Tpc 3 }

cdcp4230TpcDiskSpaceUsed OBJECT-TYPE
    SYNTAX        Integer32
    MAX-ACCESS    read-only
    STATUS        current
    DESCRIPTION
        "Returns the TPC Disk Space, Used (MB)"
    ::= { cdcp4230Tpc 4 }

cdcp4230TpcMemorySpaceAvailable OBJECT-TYPE
    SYNTAX        Integer32
    MAX-ACCESS    read-only
    STATUS        current
    DESCRIPTION
        "Returns the available TPC Memory RAM (KB)"
    ::= { cdcp4230Tpc 5 }

cdcp4230Power OBJECT IDENTIFIER ::= { cdcp4230System 2 }

cdcp4230LvpsACok OBJECT-TYPE
    SYNTAX        INTEGER {
        -- OK
        yes(1),
        -- Fail
        no(2),
        -- Not available
        na(3)
    }
    MAX-ACCESS    read-only
    STATUS        current
    DESCRIPTION
        "Returns the AC OK signal state
         1 = yes
         2 = no
         3 = Not available"
    ::= { cdcp4230Power 1 }

cdcp4230LvpsDCok OBJECT-TYPE
    SYNTAX        INTEGER {
        -- OK
        yes(1),
        -- Fail
        no(2),
        -- Not available
        na(3)
    }
    MAX-ACCESS    read-only
    STATUS        current
    DESCRIPTION
        "Returns the CC OK signal state
         1 = yes
         2 = no
         3 = Not available"
    ::= { cdcp4230Power 2 }

cdcp4230PibPowerGoodVid OBJECT-TYPE
    SYNTAX        INTEGER {
        -- OK
        yes(1),
        -- Fail
        no(2),
        -- Not available
        na(3)
    }
    MAX-ACCESS    read-only
    STATUS        current
    DESCRIPTION
        "Returns the Power Good Vid signal state
         1 = yes
         2 = no
         3 = Not available"
    ::= { cdcp4230Power 3 }

cdcp4230PibPowerGood1v2and2v5 OBJECT-TYPE
    SYNTAX        INTEGER {
        -- OK
        yes(1),
        -- Fail
        no(2),
        -- Not available
        na(3)
    }
    MAX-ACCESS    read-only
    STATUS        current
    DESCRIPTION
        "Returns the PIB PowerGood signal for the 1.2v and 2.5v rails 1
         = yes
         2 = no
         3 = Not available"
    ::= { cdcp4230Power 4 }

cdcp4230PibPowerGood1v8and3v3 OBJECT-TYPE
    SYNTAX        INTEGER {
        -- OK
        yes(1),
        -- Fail
        no(2),
        -- Not available
        na(3)
    }
    MAX-ACCESS    read-only
    STATUS        current
    DESCRIPTION
        "Returns the PIB PowerGood signal for the 1.8v and 3.3v rails 1
         = yes
         2 = no
         3 = Not available"
    ::= { cdcp4230Power 5 }

cdcp4230PibPowerGood24vEXT OBJECT-TYPE
    SYNTAX        INTEGER {
        -- OK
        yes(1),
        -- Fail
        no(2),
        -- Not available
        na(3)
    }
    MAX-ACCESS    read-only
    STATUS        current
    DESCRIPTION
        "Returns the PIB PowerGood signal for the 24v External 1 = yes
         2 = no
         3 = Not available"
    ::= { cdcp4230Power 6 }

cdcp4230PibPowerGood24vSTBY OBJECT-TYPE
    SYNTAX        INTEGER {
        -- OK
        yes(1),
        -- Fail
        no(2),
        -- Not available
        na(3)
    }
    MAX-ACCESS    read-only
    STATUS        current
    DESCRIPTION
        "Returns the PIB PowerGood signal for the 24v Standby. 1 = yes
         2 = no
         3 = Not available"
    ::= { cdcp4230Power 7 }

cdcp4230Icp1v2 OBJECT-TYPE
    SYNTAX        OCTET STRING (SIZE(1..10))
    MAX-ACCESS    read-only
    STATUS        current
    DESCRIPTION
        "Returns the ICP 1.2v rail measurements or NA if in Standby"
    ::= { cdcp4230Power 8 }

cdcp4230Icp1v8 OBJECT-TYPE
    SYNTAX        OCTET STRING (SIZE(1..10))
    MAX-ACCESS    read-only
    STATUS        current
    DESCRIPTION
        "Returns the ICP 1.8v rail measurements or NA if in Standby"
    ::= { cdcp4230Power 9 }

cdcp4230Icp2v5 OBJECT-TYPE
    SYNTAX        OCTET STRING (SIZE(1..10))
    MAX-ACCESS    read-only
    STATUS        current
    DESCRIPTION
        "Returns the ICP 2.5v rail measurements or NA if in Standby"
    ::= { cdcp4230Power 10 }

cdcp4230Icp3v3 OBJECT-TYPE
    SYNTAX        OCTET STRING (SIZE(1..10))
    MAX-ACCESS    read-only
    STATUS        current
    DESCRIPTION
        "Returns the ICP 3.3v rail measurements or NA if in Standby"
    ::= { cdcp4230Power 11 }

cdcp4230IcpCommunicating OBJECT-TYPE
    SYNTAX        TruthValue
    MAX-ACCESS    read-only
    STATUS        current
    DESCRIPTION
        "Returns IPC State:
         True = Communicating False = Not Communicating"
    ::= { cdcp4230System 3 }

cdcp4230LinkDecryptor OBJECT IDENTIFIER ::= { cdcp4230System 4 }

cdcp4230LdCommunicating OBJECT-TYPE
    SYNTAX        TruthValue
    MAX-ACCESS    read-only
    STATUS        current
    DESCRIPTION
        "Returns the ICP connection state.
         True = Communicating False = Not Communicating"
    ::= { cdcp4230LinkDecryptor 1 }

cdcp4230LdLink0 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link states:
         No Source Decryption Not Active Decryption Active Decryption
         Error Unknown"
    ::= { cdcp4230LinkDecryptor 2 }

cdcp4230LdLink1 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link1 states:
         No Source Decryption Not Active Decryption Active Decryption
         Error Unknown"
    ::= { cdcp4230LinkDecryptor 3 }

cdcp4230LdLink2 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link2 states:
         No Source Decryption Not Active Decryption Active Decryption
         Error Unknown"
    ::= { cdcp4230LinkDecryptor 4 }

cdcp4230LdLink3 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link3 states:
         No Source Decryption Not Active Decryption Active Decryption
         Error Unknown"
    ::= { cdcp4230LinkDecryptor 5 }

cdcp4230Icp OBJECT-IDENTITY
    STATUS        current
    DESCRIPTION
        "ICP related objects"
    ::= { cdcp4230System 5 }

cdcp4230IcpDiskSpaceTotal OBJECT-TYPE
    SYNTAX        Integer32
    MAX-ACCESS    read-only
    STATUS        current
    DESCRIPTION
        "Returns the available ICP Disk Space (KB)"
    ::= { cdcp4230Icp 1 }

cdcp4230IcpDiskSpaceFree OBJECT-TYPE
    SYNTAX        Integer32
    MAX-ACCESS    read-only
    STATUS        current
    DESCRIPTION
        "Returns the ICP Disk Space, Free (KB)"
    ::= { cdcp4230Icp 2 }

cdcp4230StatusPeripherals OBJECT IDENTIFIER ::= { cdcp4230Status 6 }


END
