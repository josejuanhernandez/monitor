CDS-PJTR-CP4260 DEFINITIONS ::= BEGIN

IMPORTS
    cdEsProjector
        FROM CDS-SMI
    InterfaceIndex
        FROM IF-MIB
    Gauge32, Integer32, MODULE-IDENTITY, OBJECT-IDENTITY, OBJECT-TYPE
        FROM SNMPv2-SMI
    DisplayString, MacAddress, TEXTUAL-CONVENTION, TruthValue
        FROM SNMPv2-TC
    ;

cp4260 MODULE-IDENTITY
    LAST-UPDATED  "201008031914Z" -- August 03, 2010
    ORGANIZATION
        "Christie Digital Systems, Inc."
    CONTACT-INFO
        "Christie Digital Systems
         Customer Service

         Postal:     10550 Camden Drive
         Cypress, Ca 90630
         USA

         Tel:        +1 800 221-8025

         E-mail:     support@christiedigital.com"
    DESCRIPTION
        "The MIB module for CDS Entertainment Solutions CP4260 Cinema
         projector.
         iso(1).org(3).dod(6).internet(1).private(4).enterprises(1)
         .christiedigital(25766)
         .christieDigitalProduct(1)
         .cdEs(12).cdEsProjector(1)"
    REVISION      "201103301915Z" -- March 30, 2011
    DESCRIPTION
        "Updated: IcpType to include ICP 1.5 - 16 MegaByte Flash"
    REVISION      "201009141437Z" -- September 14, 2010
    DESCRIPTION
        "Added support for ICP Disk space"
    REVISION      "201008031933Z" -- August 03, 2010
    DESCRIPTION
        "First Revision"
    ::= { cdEsProjector 8 }

-- ====================================================================
-- 
-- Versions - a table of serial numbers of install sw/hw components

Cdcp4260SerialNumberIdx ::= TEXTUAL-CONVENTION
    STATUS        current
    DESCRIPTION
        "A value used to index projector serial numbers."
    SYNTAX        Integer32 (1..64)

-- ====================================================================
-- 
-- Versions - a table of versions of install sw/hw components

Cdcp4260VersionsIdx ::= TEXTUAL-CONVENTION
    STATUS        current
    DESCRIPTION
        "A value used to index projector versions."
    SYNTAX        Integer32 (1..64)

-- ====================================================================
-- 
-- Admin only

X509Certificate ::= TEXTUAL-CONVENTION
    STATUS        current
    DESCRIPTION
        "An X509 digital certificate encoded as an ASN.1 DER object."
    SYNTAX        OCTET STRING (SIZE(0..4096))

cdcp4260Config OBJECT IDENTIFIER ::= { cp4260 1 }

cdcp4260VersionsTable OBJECT-TYPE
    SYNTAX        SEQUENCE OF Cdcp4260VersionsEntry
    MAX-ACCESS    not-accessible
    STATUS        current
    DESCRIPTION
        "A table listing the versions of the projectors hardware and
         software components."
    ::= { cdcp4260Config 1 }

cdcp4260VersionsEntry OBJECT-TYPE
    SYNTAX        Cdcp4260VersionsEntry
    MAX-ACCESS    not-accessible
    STATUS        current
    DESCRIPTION
        "The projector component description and version."
    INDEX
        { cdcp4260VersionsIndex }
    ::= { cdcp4260VersionsTable 1 }

Cdcp4260VersionsEntry ::= SEQUENCE
{
    cdcp4260VersionsIndex       Cdcp4260VersionsIdx,
    cdcp4260VersionsDescription DisplayString,
    cdcp4260VersionsVersion     DisplayString
}

cdcp4260VersionsIndex OBJECT-TYPE
    SYNTAX        Cdcp4260VersionsIdx
    MAX-ACCESS    read-only
    STATUS        current
    DESCRIPTION
        "Projector Configuration index to which the parameters in this
         row apply."
    ::= { cdcp4260VersionsEntry 1 }

cdcp4260VersionsDescription OBJECT-TYPE
    SYNTAX        DisplayString (SIZE(0..63))
    MAX-ACCESS    read-only
    STATUS        current
    DESCRIPTION
        "Component which this version entry maps to."
    ::= { cdcp4260VersionsEntry 2 }

cdcp4260VersionsVersion OBJECT-TYPE
    SYNTAX        DisplayString (SIZE(0..63))
    MAX-ACCESS    read-only
    STATUS        current
    DESCRIPTION
        "The version or serial number of the component this row
         represents.
         ."
    ::= { cdcp4260VersionsEntry 3 }

cdcp4260SerialNumberTable OBJECT-TYPE
    SYNTAX        SEQUENCE OF Cdcp4260SerialNumberEntry
    MAX-ACCESS    not-accessible
    STATUS        current
    DESCRIPTION
        "A table listing the serial numbers of the projectors hardware
         and software components."
    ::= { cdcp4260Config 2 }

cdcp4260SerialNumberEntry OBJECT-TYPE
    SYNTAX        Cdcp4260SerialNumberEntry
    MAX-ACCESS    not-accessible
    STATUS        current
    DESCRIPTION
        "The projector component description and serial number."
    INDEX
        { cdcp4260SerialNumberIndex }
    ::= { cdcp4260SerialNumberTable 1 }

Cdcp4260SerialNumberEntry ::= SEQUENCE
{
    cdcp4260SerialNumberIndex       Cdcp4260SerialNumberIdx,
    cdcp4260SerialNumberDescription DisplayString,
    cdcp4260SerialNumberVersion     DisplayString
}

cdcp4260SerialNumberIndex OBJECT-TYPE
    SYNTAX        Cdcp4260SerialNumberIdx
    MAX-ACCESS    read-only
    STATUS        current
    DESCRIPTION
        "Projector Configuration index to which the parameters in this
         row apply."
    ::= { cdcp4260SerialNumberEntry 1 }

cdcp4260SerialNumberDescription OBJECT-TYPE
    SYNTAX        DisplayString (SIZE(0..63))
    MAX-ACCESS    read-only
    STATUS        current
    DESCRIPTION
        "Component which this serial number entry maps to."
    ::= { cdcp4260SerialNumberEntry 2 }

cdcp4260SerialNumberVersion OBJECT-TYPE
    SYNTAX        DisplayString (SIZE(0..63))
    MAX-ACCESS    read-only
    STATUS        current
    DESCRIPTION
        "The serial number of the component this row represents. ."
    ::= { cdcp4260SerialNumberEntry 3 }

cdcp4260Priv OBJECT IDENTIFIER ::= { cdcp4260Config 3 }

cdcp4260CertificateIcp OBJECT-TYPE
    SYNTAX        X509Certificate
    MAX-ACCESS    read-only
    STATUS        current
    DESCRIPTION
        "This object contains the Interface Certificate.  The object
         value must be the ASN.1 DER encoding of the MTA manufacturer's
         X.509 public key certificate. ,contains the MTA's MAC  address.
         It The MTA Manufacturer Certificate is issued to each MTA
         manufacturer and is installed into each MTA at the time of
         manufacture or with a secure code download. The specific
         requirements related to this certificate are defined in  the
         Security specification."
    REFERENCE
        "Security Specification."
    ::= { cdcp4260Priv 1 }

cdcp4260IcpType OBJECT-TYPE
    SYNTAX        INTEGER {
        -- Unknown
        na(1),
        -- 8 MegaByte flash
        series2mb8(2),
        -- 16 MegaByte flash
        series2mb16(3),
        -- ICP 1.5 - 16 MegaByte flash
        series2Icp15mb16(4)
    }
    MAX-ACCESS    read-only
    STATUS        current
    DESCRIPTION
        "Returns the ICP type:
         Series2 - 8 MB flash Series2 - 16 MB flash Series2 - ICP 1.5 -
         16 MB flash"
    ::= { cdcp4260Config 4 }

cdcp4260DmdType OBJECT-TYPE
    SYNTAX        INTEGER {
        -- Not attached or unknown
        na(1),
        -- .98 inch DMD
        dc2k98(2),
        -- 2k 1.2 inch DMD
        dc2k12(3),
        -- 4k 1.38 inch DMD
        dc4k138(4)
    }
    MAX-ACCESS    read-only
    STATUS        current
    DESCRIPTION
        "Returns the DMD Type:
         2K - 0.98 inch DMD
         2K - 1.2 inch DMD
         4K - 1.38 inch DMD"
    ::= { cdcp4260Config 5 }

cdcp4260SatelliteType OBJECT IDENTIFIER ::= { cdcp4260Config 6 }

cdcp4260RedSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4260SatelliteType 1 }

cdcp4260GreenSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4260SatelliteType 2 }

cdcp4260BlueSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp4260SatelliteType 3 }

cdcp4260Peripherals OBJECT IDENTIFIER ::= { cdcp4260Config 7 }

cdcp4260IlsInstalled OBJECT-TYPE
    SYNTAX        TruthValue
    MAX-ACCESS    read-only
    STATUS        current
    DESCRIPTION
        "Returns true if ILS is installed otherwise returns false."
    ::= { cdcp4260Peripherals 1 }

cdcp4260OptionCardInsalled OBJECT-TYPE
    SYNTAX        TruthValue
    MAX-ACCESS    not-accessible
    STATUS        current
    DESCRIPTION
        "Returns true if Option Card is installed, otherwise returns
         false."
    ::= { cdcp4260Peripherals 2 }

cdcp4260MediaBlockInstalled OBJECT-TYPE
    SYNTAX        TruthValue
    MAX-ACCESS    read-only
    STATUS        current
    DESCRIPTION
        "Returns true if MediaBlock is installed otherwise returns
         false."
    ::= { cdcp4260Peripherals 3 }

cdcp4260LaserTable OBJECT-TYPE
    SYNTAX        SEQUENCE OF Cdcp4260LaserEntry
    MAX-ACCESS    not-accessible
    STATUS        current
    DESCRIPTION
        ""
    ::= { cdcp4260Config 8 }

cdcp4260LaserEntry OBJECT-TYPE
    SYNTAX        Cdcp4260LaserEntry
    MAX-ACCESS    not-accessible
    STATUS        current
    DESCRIPTION
        ""
    INDEX
        { cdcp4260LaserIndex, cdcp4260LaserElectronicId }
    ::= { cdcp4260LaserTable 1 }

Cdcp4260LaserEntry ::= SEQUENCE
{
    cdcp4260LaserElectronicId DisplayString,
    cdcp4260LaserType         DisplayString,
    cdcp4260LaserBootSwVer    DisplayString,
    cdcp4260LaserMainSwVer    DisplayString,
    cdcp4260LaserHwVer        DisplayString,
    cdcp4260LaserSerialNum    DisplayString,
    cdcp4260LaserBuildDate    DisplayString
}

cdcp4260LaserIndex OBJECT-TYPE
    SYNTAX        Integer32
    MAX-ACCESS    not-accessible
    STATUS        current
    DESCRIPTION
        ""
    ::= { cdcp4260LaserEntry 1 }

cdcp4260LaserElectronicId OBJECT-TYPE
    SYNTAX        DisplayString
    MAX-ACCESS    read-only
    STATUS        current
    DESCRIPTION
        ""
    ::= { cdcp4260LaserEntry 2 }

cdcp4260LaserType OBJECT-TYPE
    SYNTAX        DisplayString
    MAX-ACCESS    read-only
    STATUS        current
    DESCRIPTION
        ""
    ::= { cdcp4260LaserEntry 3 }

cdcp4260LaserBootSwVer OBJECT-TYPE
    SYNTAX        DisplayString
    MAX-ACCESS    read-only
    STATUS        current
    DESCRIPTION
        ""
    ::= { cdcp4260LaserEntry 4 }

cdcp4260LaserMainSwVer OBJECT-TYPE
    SYNTAX        DisplayString
    MAX-ACCESS    read-only
    STATUS        current
    DESCRIPTION
        ""
    ::= { cdcp4260LaserEntry 5 }

cdcp4260LaserHwVer OBJECT-TYPE
    SYNTAX        DisplayString
    MAX-ACCESS    read-only
    STATUS        current
    DESCRIPTION
        ""
    ::= { cdcp4260LaserEntry 6 }

cdcp4260LaserSerialNum OBJECT-TYPE
    SYNTAX        DisplayString
    MAX-ACCESS    read-only
    STATUS        current
    DESCRIPTION
        ""
    ::= { cdcp4260LaserEntry 7 }

cdcp4260LaserBuildDate OBJECT-TYPE
    SYNTAX        DisplayString
    MAX-ACCESS    read-only
    STATUS        current
    DESCRIPTION
        ""
    ::= { cdcp4260LaserEntry 8 }

newObjectType OBJECT-TYPE
    SYNTAX        Integer32
    MAX-ACCESS    not-accessible
    STATUS        current
    DESCRIPTION
        ""
    ::= { cdcp4260LaserEntry 9 }

cdcp4260Status OBJECT IDENTIFIER ::= { cp4260 2 }

-- ====================================================================
-- 
-- Security status group

cdcp4260SecurityStatus OBJECT IDENTIFIER ::= { cdcp4260Status 1 }

cdcp4260SecurityArmed OBJECT-TYPE
    SYNTAX        INTEGER {
        armed(1),
        notArmed(2),
        na(3)
    }
    MAX-ACCESS    read-only
    STATUS        current
    DESCRIPTION
        "Security enclosure armed."
    ::= { cdcp4260SecurityStatus 1 }

cdcp4260SecurityTamper OBJECT-TYPE
    SYNTAX        INTEGER {
        tamper(1),
        secure(2),
        na(3)
    }
    MAX-ACCESS    read-only
    STATUS        current
    DESCRIPTION
        "Security enclosure tamper."
    ::= { cdcp4260SecurityStatus 2 }

cdcp4260MarriageActive OBJECT-TYPE
    SYNTAX        INTEGER {
        married(1),
        marriageBroken(2),
        na(3)
    }
    MAX-ACCESS    read-only
    STATUS        current
    DESCRIPTION
        "Marriage State,  When marriage is broken, no encrypted content
         can be played."
    ::= { cdcp4260SecurityStatus 3 }

cdcp4260PhysicalMarriageTamper OBJECT-TYPE
    SYNTAX        INTEGER {
        tampered(1),
        secure(2),
        na(3)
    }
    MAX-ACCESS    read-only
    STATUS        current
    DESCRIPTION
        "Physical Marriage State, Removal of any board within the card
         cage will cause a Physical tamper."
    ::= { cdcp4260SecurityStatus 4 }

cdcp4260LogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the LD board or Image Media Block."
    ::= { cdcp4260SecurityStatus 5 }

cdcp4260SoftwareCertZeroization OBJECT-TYPE
    SYNTAX        INTEGER {
        zeroed(1),
        ok(2),
        na(3)
    }
    MAX-ACCESS    read-only
    STATUS        current
    DESCRIPTION
        "Certificate State, A zeroed certificate state indicates  that
         a tamper has occurred on the LD board."
    ::= { cdcp4260SecurityStatus 6 }

cdcp4260ServiceDoorTamper OBJECT-TYPE
    SYNTAX        INTEGER {
        tamper(1),
        secure(2),
        na(3)
    }
    MAX-ACCESS    read-only
    STATUS        current
    DESCRIPTION
        "Service door to light engine compartment"
    ::= { cdcp4260SecurityStatus 7 }

cdcp4260TopEnclosureOpen OBJECT-TYPE
    SYNTAX        INTEGER {
        tamper(1),
        secure(2),
        na(3)
    }
    MAX-ACCESS    read-only
    STATUS        current
    DESCRIPTION
        "Security enclosure state, top side."
    ::= { cdcp4260SecurityStatus 8 }

cdcp4260BottomEnclosureOpen OBJECT-TYPE
    SYNTAX        INTEGER {
        tamper(1),
        secure(2),
        na(3)
    }
    MAX-ACCESS    read-only
    STATUS        current
    DESCRIPTION
        "Security enclosure state, top side."
    ::= { cdcp4260SecurityStatus 9 }

cdcp4260SecurityBatteryEvent OBJECT-TYPE
    SYNTAX        INTEGER {
        failed(1),
        ok(2),
        na(3)
    }
    MAX-ACCESS    read-only
    STATUS        current
    DESCRIPTION
        "Battery failed"
    ::= { cdcp4260SecurityStatus 10 }

cdcp4260BatteryLow OBJECT-TYPE
    SYNTAX        INTEGER {
        low(1),
        ok(2),
        na(3)
    }
    MAX-ACCESS    read-only
    STATUS        current
    DESCRIPTION
        "Battery state."
    ::= { cdcp4260SecurityStatus 11 }

cdcp4260SecurityLog OBJECT-TYPE
    SYNTAX        INTEGER {
        ok(1),
        warning(2),
        error(3),
        na(4)
    }
    MAX-ACCESS    read-only
    STATUS        current
    DESCRIPTION
        "The Security Log Warning indicates that there are  less than
         100 log entry locations available before  unread log entries
         will be overwritten.

         The Security Log Error indicates that there is no  more room to
         write log entries.

         When this warning/error is active, the Server needs  to extract
         the log data (via ASM/TLS session) from  the LD Security Log.
         Reads of the security log by any other entity/means will not
         impact this warning."
    ::= { cdcp4260SecurityStatus 12 }

-- ====================================================================
-- 
-- Sensor tables

cdcp4260Sensors OBJECT IDENTIFIER ::= { cdcp4260Status 2 }

cdcp4260TempSensorsTable OBJECT-TYPE
    SYNTAX        SEQUENCE OF Cdcp4260TempSensorsEntry
    MAX-ACCESS    not-accessible
    STATUS        current
    DESCRIPTION
        "Table of temperature sensors and their values."
    ::= { cdcp4260Sensors 1 }

cdcp4260TempSensorsEntry OBJECT-TYPE
    SYNTAX        Cdcp4260TempSensorsEntry
    MAX-ACCESS    not-accessible
    STATUS        current
    DESCRIPTION
        "An entry containing a device and its statistics."
    INDEX
        { cdcp4260TempSensorsIndex }
    ::= { cdcp4260TempSensorsTable 1 }

Cdcp4260TempSensorsEntry ::= SEQUENCE
{
    cdcp4260TempSensorsIndex      Integer32,
    cdcp4260TempSensorsDevice     DisplayString,
    cdcp4260TempSensorsDiodeError TruthValue,
    cdcp4260TempSensorsLowerLimit TruthValue,
    cdcp4260TempSensorsUpperLimit TruthValue,
    cdcp4260TempSensorsValue      Gauge32
}

cdcp4260TempSensorsIndex OBJECT-TYPE
    SYNTAX        Integer32 (0..65535)
    MAX-ACCESS    read-only
    STATUS        current
    DESCRIPTION
        "Reference index for each observed device."
    ::= { cdcp4260TempSensorsEntry 1 }

cdcp4260TempSensorsDevice OBJECT-TYPE
    SYNTAX        DisplayString (SIZE(0..63))
    MAX-ACCESS    read-only
    STATUS        current
    DESCRIPTION
        "The name of the temperature sensor we are reading."
    ::= { cdcp4260TempSensorsEntry 2 }

cdcp4260TempSensorsState OBJECT-TYPE
    SYNTAX        INTEGER {
        -- Not Avaliable
        na(1),
        -- OK
        ok(2),
        -- Sensor fail
        fail(3),
        -- Under Temperature Alarm
        underTempAlarm(4),
        -- Under Temperature Warning
        underTempWarning(5),
        -- Over Temperature Warning
        overTempWarning(6),
        -- Over Temperature Alarm
        overTempAlarm(7)
    }
    MAX-ACCESS    read-only
    STATUS        current
    DESCRIPTION
        "Returns the state of the temperature sensor."
    ::= { cdcp4260TempSensorsEntry 3 }

cdcp4260TempSensorsValue OBJECT-TYPE
    SYNTAX        INTEGER
    MAX-ACCESS    read-only
    STATUS        current
    DESCRIPTION
        "The temperature of this sensor in Celsius"
    ::= { cdcp4260TempSensorsEntry 4 }

cdcp4260TempThresLowerAlarm OBJECT-TYPE
    SYNTAX        INTEGER
    MAX-ACCESS    read-only
    STATUS        current
    DESCRIPTION
        "True if the sensor has breached it's lower limit."
    ::= { cdcp4260TempSensorsEntry 5 }

cdcp4260TempThresLowerWarning OBJECT-TYPE
    SYNTAX        INTEGER
    MAX-ACCESS    not-accessible
    STATUS        current
    DESCRIPTION
        "This is the threshold where the lower temperature Warning will
         be tripped."
    ::= { cdcp4260TempSensorsEntry 6 }

cdcp4260TempThresUpperWarning OBJECT-TYPE
    SYNTAX        INTEGER
    MAX-ACCESS    not-accessible
    STATUS        current
    DESCRIPTION
        "This is the threshold where the Upper temperature warning will
         be tripped."
    ::= { cdcp4260TempSensorsEntry 7 }

cdcp4260TempThresUpperAlarm OBJECT-TYPE
    SYNTAX        INTEGER
    MAX-ACCESS    read-only
    STATUS        current
    DESCRIPTION
        "This is the threshold where the upper temperature Alarm will
         be tripped."
    ::= { cdcp4260TempSensorsEntry 8 }

cdcp4260FanSensorsTable OBJECT-TYPE
    SYNTAX        SEQUENCE OF Cdcp4260FanSensorsEntry
    MAX-ACCESS    not-accessible
    STATUS        current
    DESCRIPTION
        "Table of fan sensors and their values."
    ::= { cdcp4260Sensors 2 }

cdcp4260FanSensorsEntry OBJECT-TYPE
    SYNTAX        Cdcp4260FanSensorsEntry
    MAX-ACCESS    not-accessible
    STATUS        current
    DESCRIPTION
        "An entry containing a device and its statistics."
    INDEX
        { cdcp4260FanSensorsIndex }
    ::= { cdcp4260FanSensorsTable 1 }

Cdcp4260FanSensorsEntry ::= SEQUENCE
{
    cdcp4260FanSensorsIndex   Integer32,
    cdcp4260FanSensorsDevice  DisplayString,
    cdcp4260FanSensorsFault   TruthValue,
    cdcp4260FanSensorsTooSlow TruthValue,
    cdcp4260FanSensorsValue   Gauge32
}

cdcp4260FanSensorsIndex OBJECT-TYPE
    SYNTAX        Integer32 (0..65535)
    MAX-ACCESS    read-only
    STATUS        current
    DESCRIPTION
        "Reference index for each observed device."
    ::= { cdcp4260FanSensorsEntry 1 }

cdcp4260FanSensorsDevice OBJECT-TYPE
    SYNTAX        DisplayString (SIZE(0..63))
    MAX-ACCESS    read-only
    STATUS        current
    DESCRIPTION
        "The name of the fan sensor we are reading."
    ::= { cdcp4260FanSensorsEntry 2 }

cdcp4260FanSensorsState OBJECT-TYPE
    SYNTAX        INTEGER {
        -- Not Avaliable
        na(1),
        -- Fan is off
        off(2),
        -- Fan is running within tolerance
        ok(3),
        -- Fan has failed
        failed(4),
        -- Fan is running way too slow
        alarm(5),
        -- Fan is running slower than expected
        warning(6)
    }
    MAX-ACCESS    read-only
    STATUS        current
    DESCRIPTION
        "Returns the state of the temperature sensor."
    ::= { cdcp4260FanSensorsEntry 3 }

cdcp4260FanSensorsValue OBJECT-TYPE
    SYNTAX        INTEGER
    MAX-ACCESS    read-only
    STATUS        current
    DESCRIPTION
        "The rotation speed of the fan in RPM."
    ::= { cdcp4260FanSensorsEntry 5 }

cdcp4260FanThresLowerAlarm OBJECT-TYPE
    SYNTAX        INTEGER
    MAX-ACCESS    read-only
    STATUS        current
    DESCRIPTION
        "This is the threshold where the lower fan Alarm will be
         tripped."
    ::= { cdcp4260FanSensorsEntry 6 }

dcp4260FanThresLowerWarning OBJECT-TYPE
    SYNTAX        INTEGER
    MAX-ACCESS    not-accessible
    STATUS        current
    DESCRIPTION
        "This is the threshold where the lower fan Warning will be
         tripped."
    ::= { cdcp4260FanSensorsEntry 7 }

cdcp4260InterlockSensorsTable OBJECT-TYPE
    SYNTAX        SEQUENCE OF Cdcp4260InterlockSensorsEntry
    MAX-ACCESS    not-accessible
    STATUS        current
    DESCRIPTION
        "Table of interlock sensors and their value."
    ::= { cdcp4260Sensors 3 }

cdcp4260InterlockSensorsEntry OBJECT-TYPE
    SYNTAX        Cdcp4260InterlockSensorsEntry
    MAX-ACCESS    not-accessible
    STATUS        current
    DESCRIPTION
        "An entry containing a device and its statistics."
    INDEX
        { cdcp4260InterlockSensorsIndex }
    ::= { cdcp4260InterlockSensorsTable 1 }

Cdcp4260InterlockSensorsEntry ::= SEQUENCE
{
    cdcp4260InterlockSensorsIndex  Integer32,
    cdcp4260InterlockSensorsDevice DisplayString,
    cdcp4260InterlockSensorsValue  INTEGER
}

cdcp4260InterlockSensorsIndex OBJECT-TYPE
    SYNTAX        Integer32 (0..65535)
    MAX-ACCESS    read-only
    STATUS        current
    DESCRIPTION
        "Reference index for each observed device."
    ::= { cdcp4260InterlockSensorsEntry 1 }

cdcp4260InterlockSensorsDevice OBJECT-TYPE
    SYNTAX        DisplayString (SIZE(0..63))
    MAX-ACCESS    read-only
    STATUS        current
    DESCRIPTION
        "The name of the interlock sensor we are reading."
    ::= { cdcp4260InterlockSensorsEntry 2 }

cdcp4260InterlockSensorsState OBJECT-TYPE
    SYNTAX        INTEGER {
        -- Not available
        na(1),
        open(2),
        closed(3),
        troubleOpen(4),
        troubleClosed(5)
    }
    MAX-ACCESS    read-only
    STATUS        current
    DESCRIPTION
        "The status of this interlock."
    ::= { cdcp4260InterlockSensorsEntry 3 }

-- ====================================================================
-- 
-- System health table, reports diagnostic test results.

cdcp4260SystemHealthTable OBJECT-TYPE
    SYNTAX        SEQUENCE OF Cdcp4260SystemHealthEntry
    MAX-ACCESS    not-accessible
    STATUS        current
    DESCRIPTION
        "Table of diagnostic tests and their results"
    ::= { cdcp4260Status 3 }

cdcp4260SystemHealthEntry OBJECT-TYPE
    SYNTAX        Cdcp4260SystemHealthEntry
    MAX-ACCESS    not-accessible
    STATUS        current
    DESCRIPTION
        "Each row respresents a diagnostic test and the result."
    INDEX
        { cdcp4260SystemHealthIndex }
    ::= { cdcp4260SystemHealthTable 1 }

Cdcp4260SystemHealthEntry ::= SEQUENCE
{
    cdcp4260SystemHealthIndex  Integer32,
    cdcp4260SystemHealthName   DisplayString,
    cdcp4260SystemHealthResult DisplayString
}

cdcp4260SystemHealthIndex OBJECT-TYPE
    SYNTAX        Integer32 (0..65535)
    MAX-ACCESS    read-only
    STATUS        current
    DESCRIPTION
        "Reference index for each observed test."
    ::= { cdcp4260SystemHealthEntry 1 }

cdcp4260SystemHealthName OBJECT-TYPE
    SYNTAX        DisplayString (SIZE(0..127))
    MAX-ACCESS    read-only
    STATUS        current
    DESCRIPTION
        "Name of the diagnostic being reported."
    ::= { cdcp4260SystemHealthEntry 2 }

cdcp4260SystemHealthResult OBJECT-TYPE
    SYNTAX        DisplayString (SIZE(0..127))
    MAX-ACCESS    read-only
    STATUS        current
    DESCRIPTION
        "Result of diagnostic."
    ::= { cdcp4260SystemHealthEntry 3 }

cdcp4260Lens OBJECT-IDENTITY
    STATUS        current
    DESCRIPTION
        "Contains information about the Primary Lens"
    ::= { cdcp4260Status 4 }

cdcp4260LensType OBJECT-TYPE
    SYNTAX        DisplayString (0..255)
    MAX-ACCESS    not-accessible
    STATUS        current
    DESCRIPTION
        "Lens Type"
    ::= { cdcp4260Lens 1 }

cdcp4260LensSerialNumber OBJECT-TYPE
    SYNTAX        DisplayString (SIZE(0..255))
    MAX-ACCESS    read-only
    STATUS        current
    DESCRIPTION
        "Lens Serial Number"
    ::= { cdcp4260Lens 2 }

cdcp4260System OBJECT IDENTIFIER ::= { cdcp4260Status 5 }

cdcp4260Tpc OBJECT IDENTIFIER ::= { cdcp4260System 1 }

cdcp4260TpcType OBJECT-TYPE
    SYNTAX        OCTET STRING
    MAX-ACCESS    read-only
    STATUS        current
    DESCRIPTION
        "Returns the TPC Type:
         TPC-660E TPC-650H"
    ::= { cdcp4260Tpc 1 }

cdcp4260TpcOs OBJECT-TYPE
    SYNTAX        OCTET STRING
    MAX-ACCESS    read-only
    STATUS        current
    DESCRIPTION
        "Returns the TPC OS Image"
    ::= { cdcp4260Tpc 2 }

cdcp4260TpcDiskSpaceAvailable OBJECT-TYPE
    SYNTAX        Integer32
    MAX-ACCESS    read-only
    STATUS        current
    DESCRIPTION
        "Returns the available TPC Disk Space"
    ::= { cdcp4260Tpc 3 }

cdcp4260TpcDiskSpaceUsed OBJECT-TYPE
    SYNTAX        Integer32
    MAX-ACCESS    read-only
    STATUS        current
    DESCRIPTION
        "Returns the TPC Disk Space, Used (MB)"
    ::= { cdcp4260Tpc 4 }

cdcp4260TpcMemorySpaceAvailable OBJECT-TYPE
    SYNTAX        Integer32
    MAX-ACCESS    read-only
    STATUS        current
    DESCRIPTION
        "Returns the available TPC Memory RAM (KB)"
    ::= { cdcp4260Tpc 5 }

cdcp4260Power OBJECT IDENTIFIER ::= { cdcp4260System 2 }

cdcp4260LvpsACok OBJECT-TYPE
    SYNTAX        INTEGER {
        -- OK
        yes(1),
        -- Fail
        no(2),
        -- Not available
        na(3)
    }
    MAX-ACCESS    read-only
    STATUS        current
    DESCRIPTION
        "Returns the AC OK signal state
         1 = yes
         2 = no
         3 = Not available"
    ::= { cdcp4260Power 1 }

cdcp4260LvpsDCok OBJECT-TYPE
    SYNTAX        INTEGER {
        -- OK
        yes(1),
        -- Fail
        no(2),
        -- Not available
        na(3)
    }
    MAX-ACCESS    read-only
    STATUS        current
    DESCRIPTION
        "Returns the CC OK signal state
         1 = yes
         2 = no
         3 = Not available"
    ::= { cdcp4260Power 2 }

cdcp4260PibPowerGoodVid OBJECT-TYPE
    SYNTAX        INTEGER {
        -- OK
        yes(1),
        -- Fail
        no(2),
        -- Not available
        na(3)
    }
    MAX-ACCESS    read-only
    STATUS        current
    DESCRIPTION
        "Returns the Power Good Vid signal state
         1 = yes
         2 = no
         3 = Not available"
    ::= { cdcp4260Power 3 }

cdcp4260PibPowerGood1v2and2v5 OBJECT-TYPE
    SYNTAX        INTEGER {
        -- OK
        yes(1),
        -- Fail
        no(2),
        -- Not available
        na(3)
    }
    MAX-ACCESS    read-only
    STATUS        current
    DESCRIPTION
        "Returns the PIB PowerGood signal for the 1.2v and 2.5v rails 1
         = yes
         2 = no
         3 = Not available"
    ::= { cdcp4260Power 4 }

cdcp4260PibPowerGood1v8and3v3 OBJECT-TYPE
    SYNTAX        INTEGER {
        -- OK
        yes(1),
        -- Fail
        no(2),
        -- Not available
        na(3)
    }
    MAX-ACCESS    read-only
    STATUS        current
    DESCRIPTION
        "Returns the PIB PowerGood signal for the 1.8v and 3.3v rails 1
         = yes
         2 = no
         3 = Not available"
    ::= { cdcp4260Power 5 }

cdcp4260PibPowerGood24vEXT OBJECT-TYPE
    SYNTAX        INTEGER {
        -- OK
        yes(1),
        -- Fail
        no(2),
        -- Not available
        na(3)
    }
    MAX-ACCESS    read-only
    STATUS        current
    DESCRIPTION
        "Returns the PIB PowerGood signal for the 24v External 1 = yes
         2 = no
         3 = Not available"
    ::= { cdcp4260Power 6 }

cdcp4260PibPowerGood24vSTBY OBJECT-TYPE
    SYNTAX        INTEGER {
        -- OK
        yes(1),
        -- Fail
        no(2),
        -- Not available
        na(3)
    }
    MAX-ACCESS    read-only
    STATUS        current
    DESCRIPTION
        "Returns the PIB PowerGood signal for the 24v Standby. 1 = yes
         2 = no
         3 = Not available"
    ::= { cdcp4260Power 7 }

cdcp4260Icp1v2 OBJECT-TYPE
    SYNTAX        OCTET STRING (SIZE(1..10))
    MAX-ACCESS    read-only
    STATUS        current
    DESCRIPTION
        "Returns the ICP 1.2v rail measurements or NA if in Standby"
    ::= { cdcp4260Power 8 }

cdcp4260Icp1v8 OBJECT-TYPE
    SYNTAX        OCTET STRING (SIZE(1..10))
    MAX-ACCESS    read-only
    STATUS        current
    DESCRIPTION
        "Returns the ICP 1.8v rail measurements or NA if in Standby"
    ::= { cdcp4260Power 9 }

cdcp4260Icp2v5 OBJECT-TYPE
    SYNTAX        OCTET STRING (SIZE(1..10))
    MAX-ACCESS    read-only
    STATUS        current
    DESCRIPTION
        "Returns the ICP 2.5v rail measurements or NA if in Standby"
    ::= { cdcp4260Power 10 }

cdcp4260Icp3v3 OBJECT-TYPE
    SYNTAX        OCTET STRING (SIZE(1..10))
    MAX-ACCESS    read-only
    STATUS        current
    DESCRIPTION
        "Returns the ICP 3.3v rail measurements or NA if in Standby"
    ::= { cdcp4260Power 11 }

cdcp4260LinkDecryptor OBJECT IDENTIFIER ::= { cdcp4260System 4 }

cdcp4260LdCommunicating OBJECT-TYPE
    SYNTAX        TruthValue
    MAX-ACCESS    read-only
    STATUS        current
    DESCRIPTION
        "Returns the ICP connection state. True = Communicating False =
         Not Communicating"
    ::= { cdcp4260LinkDecryptor 1 }

cdcp4260LdLink0 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link states:
         No Source Decryption Not Active Decryption Active Decryption
         Error Unknown"
    ::= { cdcp4260LinkDecryptor 2 }

cdcp4260LdLink1 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link1 states:
         No Source Decryption Not Active Decryption Active Decryption
         Error Unknown"
    ::= { cdcp4260LinkDecryptor 3 }

cdcp4260LdLink2 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link2 states:
         No Source Decryption Not Active Decryption Active Decryption
         Error Unknown"
    ::= { cdcp4260LinkDecryptor 4 }

cdcp4260LdLink3 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link3 states:
         No Source Decryption Not Active Decryption Active Decryption
         Error Unknown"
    ::= { cdcp4260LinkDecryptor 5 }

cdcp4260Icp OBJECT-IDENTITY
    STATUS        current
    DESCRIPTION
        "ICP related objects"
    ::= { cdcp4260System 5 }

cdcp4260IcpCommunicating OBJECT-TYPE
    SYNTAX        TruthValue
    MAX-ACCESS    read-only
    STATUS        current
    DESCRIPTION
        "Returns IPC State:
         True = Communicating False = Not Communicating"
    ::= { cdcp4260Icp 1 }

cdcp4260IcpDiskSpaceTotal OBJECT-TYPE
    SYNTAX        Integer32
    MAX-ACCESS    read-only
    STATUS        current
    DESCRIPTION
        "Returns the available ICP Disk Space (KB)"
    ::= { cdcp4260Icp 2 }

cdcp4260IcpDiskSpaceFree OBJECT-TYPE
    SYNTAX        Integer32
    MAX-ACCESS    read-only
    STATUS        current
    DESCRIPTION
        "Returns the ICP Disk Space, Free (KB)"
    ::= { cdcp4260Icp 3 }

cdcp4260StatusPeripherals OBJECT IDENTIFIER ::= { cdcp4260Status 6 }

cdcp4260LaserStatusTable OBJECT-TYPE
    SYNTAX        SEQUENCE OF Cdcp4260LaserStatusEntry
    MAX-ACCESS    not-accessible
    STATUS        current
    DESCRIPTION
        ""
    ::= { cdcp4260Status 7 }

cdcp4260LaserStatusEntry OBJECT-TYPE
    SYNTAX        Cdcp4260LaserStatusEntry
    MAX-ACCESS    not-accessible
    STATUS        current
    DESCRIPTION
        ""
    INDEX
        { cdcp4260LaserStatusLaserIndex, cdcp4260LaserStatusElectronicId
        }
    ::= { cdcp4260LaserStatusTable 1 }

Cdcp4260LaserStatusEntry ::= SEQUENCE
{
    cdcp4260LaserStatusLaserIndex   Integer32,
    cdcp4260LaserStatusElectronicId DisplayString,
    cdcp4260LaserStatusState        INTEGER
}

cdcp4260LaserStatusLaserIndex OBJECT-TYPE
    SYNTAX        Integer32
    MAX-ACCESS    not-accessible
    STATUS        current
    DESCRIPTION
        ""
    ::= { cdcp4260LaserStatusEntry 1 }

cdcp4260LaserStatusElectronicId OBJECT-TYPE
    SYNTAX        DisplayString
    MAX-ACCESS    not-accessible
    STATUS        current
    DESCRIPTION
        ""
    ::= { cdcp4260LaserStatusEntry 2 }

cdcp4260LaserStatusState OBJECT-TYPE
    SYNTAX        INTEGER
    MAX-ACCESS    read-only
    STATUS        current
    DESCRIPTION
        ""
    ::= { cdcp4260LaserStatusEntry 3 }

END
