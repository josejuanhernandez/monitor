CDS-PJTR-CP2210R-NOTIFY DEFINITIONS ::= BEGIN

IMPORTS
    cp2210R
        FROM CDS-PJTR-CP2210R
    NOTIFICATION-GROUP, OBJECT-GROUP
        FROM SNMPv2-CONF
    MODULE-IDENTITY, NOTIFICATION-TYPE, OBJECT-TYPE
        FROM SNMPv2-SMI
    DisplayString
        FROM SNMPv2-TC
    ;

cdcp2210RNotification MODULE-IDENTITY
    LAST-UPDATED  "201212191650Z" -- December 19, 2012
    ORGANIZATION
        "Christie Digital Systems, Inc."
    CONTACT-INFO
        "Christie Digital Systems
         Customer Service

         Postal:  10550 Camden Drive
         Cypress, Ca 90630
         USA

         Tel:  +1 800 221-8025

         E-mail:  support@cds.com"
    DESCRIPTION
        "The MIB module for CDS cinema projector notifications. Alarms
         correspond to those generated within the TPC  and are
         documented in the manual."
    REVISION      "201212191650Z" -- December 19, 2012
    DESCRIPTION
        "Replaced LampLifeRotation with the LampHalfLife notification."

    ::= { cp2210R 100 }

cdcp2210RNotificationGroups OBJECT IDENTIFIER ::= { cdcp2210RNotification 1 }

-- ====================================================================
-- 
-- Object groups

cdcp2210RNotificationObjectsGroup OBJECT-GROUP
    OBJECTS
        { cdSensorName, cdSensorValue, cdComponentName, cdLampHours,
        cdTamperName, cdTamperValue }
    STATUS        current
    DESCRIPTION
        "Notification objects"
    ::= { cdcp2210RNotificationGroups 1 }

-- cdcp2210RNotificationGroup OBJECT-GROUP OBJECTS

cdcp2210RNotificationGroup NOTIFICATION-GROUP
    NOTIFICATIONS
        { cdcp2210RNotifyFan, cdcp2210RNotifyInterlock,
        cdcp2210RNotifyTemperature, cdcp2210RNotifySystemComm,
        cdcp2210RNotifyLampStrike,
        cdcp2210RNotifyLampUnexpectedOff, cdcp2210RNotifySecurityTamper,
        cdcp2210RNotifyCoolant }
    STATUS        current
    DESCRIPTION
        "Notifications"
    ::= { cdcp2210RNotificationGroups 2 }

cdcp2210RNotificationObjects OBJECT IDENTIFIER ::= { cdcp2210RNotification 2 }

-- ====================================================================
-- 
-- Notification objects

cdSensorName OBJECT-TYPE
    SYNTAX        DisplayString
    MAX-ACCESS    accessible-for-notify
    STATUS        current
    DESCRIPTION
        "Identifies the specific sensor which triggered the
         notification."
    ::= { cdcp2210RNotificationObjects 1 }

cdSensorValue OBJECT-TYPE
    SYNTAX        DisplayString
    MAX-ACCESS    accessible-for-notify
    STATUS        current
    DESCRIPTION
        "A string with the formatted value of the sensor which
         triggered the notification."
    ::= { cdcp2210RNotificationObjects 2 }

cdComponentName OBJECT-TYPE
    SYNTAX        DisplayString
    MAX-ACCESS    accessible-for-notify
    STATUS        current
    DESCRIPTION
        "Descripes the component which caused a comm error to trigger
         the notification."
    ::= { cdcp2210RNotificationObjects 3 }

cdLampHours OBJECT-TYPE
    SYNTAX        INTEGER (0..65535)
    MAX-ACCESS    accessible-for-notify
    STATUS        current
    DESCRIPTION
        "Hours the installed lamp has operated."
    ::= { cdcp2210RNotificationObjects 4 }

cdTamperName OBJECT-TYPE
    SYNTAX        DisplayString
    MAX-ACCESS    accessible-for-notify
    STATUS        current
    DESCRIPTION
        "Identifies the specific tamper which triggered the
         notification."
    ::= { cdcp2210RNotificationObjects 5 }

cdTamperValue OBJECT-TYPE
    SYNTAX        DisplayString
    MAX-ACCESS    accessible-for-notify
    STATUS        current
    DESCRIPTION
        "A string with the formatted value of the tamper which
         triggered the notification."
    ::= { cdcp2210RNotificationObjects 6 }

cdcp2210RNotifications OBJECT IDENTIFIER ::= { cdcp2210RNotification 3 }

cdcp2210RNotificationsPrefix OBJECT IDENTIFIER ::= { cdcp2210RNotifications 0 }

-- ====================================================================
-- 
-- Projector notifications

cdcp2210RNotifyFan NOTIFICATION-TYPE
    OBJECTS
        { cdSensorName, cdSensorValue }
    STATUS        current
    DESCRIPTION
        "A fan speed error has occured."
    ::= { cdcp2210RNotificationsPrefix 1 }

cdcp2210RNotifyInterlock NOTIFICATION-TYPE
    OBJECTS
        { cdSensorName, cdSensorValue }
    STATUS        current
    DESCRIPTION
        "An interlock was tripped."
    ::= { cdcp2210RNotificationsPrefix 2 }

cdcp2210RNotifyTemperature NOTIFICATION-TYPE
    OBJECTS
        { cdSensorName, cdSensorValue }
    STATUS        current
    DESCRIPTION
        "Temperature sensor breached operational threshold."
    ::= { cdcp2210RNotificationsPrefix 3 }

cdcp2210RNotifySystemComm NOTIFICATION-TYPE
    OBJECTS
        { cdComponentName }
    STATUS        current
    DESCRIPTION
        "Communications to critical system component failed."
    ::= { cdcp2210RNotificationsPrefix 4 }

cdcp2210RNotifyLampStrike NOTIFICATION-TYPE
    OBJECTS
        { cdLampHours }
    STATUS        current
    DESCRIPTION
        "Lamp failed to strike."
    ::= { cdcp2210RNotificationsPrefix 6 }

cdcp2210RNotifyLampUnexpectedOff NOTIFICATION-TYPE
    OBJECTS
        { cdLampHours }
    STATUS        current
    DESCRIPTION
        "Unexpected lamp failure."
    ::= { cdcp2210RNotificationsPrefix 7 }

cdcp2210RNotifyCoolant NOTIFICATION-TYPE
    STATUS        current
    DESCRIPTION
        "Liquid cooling pump failure"
    ::= { cdcp2210RNotificationsPrefix 8 }

cdcp2210RNotifySecurityTamper NOTIFICATION-TYPE
    OBJECTS
        { cdTamperName, cdTamperValue }
    STATUS        current
    DESCRIPTION
        "Security System has been tampered tamper name and tamper
         state."
    ::= { cdcp2210RNotificationsPrefix 10 }

END
