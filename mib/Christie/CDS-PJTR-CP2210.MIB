CDS-PJTR-CP2210 DEFINITIONS ::= BEGIN

IMPORTS
    cdEsProjector
        FROM CDS-SMI
    Gauge32, Integer32, MODULE-IDENTITY, OBJECT-IDENTITY, OBJECT-TYPE
        FROM SNMPv2-SMI
    DisplayString, TEXTUAL-CONVENTION, TruthValue
        FROM SNMPv2-TC
    ;

cp2210 MODULE-IDENTITY
    LAST-UPDATED  "201008031914Z" -- August 03, 2010
    ORGANIZATION
        "Christie Digital Systems, Inc."
    CONTACT-INFO
        "Christie Digital Systems
         Customer Service

         Postal:     10550 Camden Drive
         Cypress, Ca 90630
         USA

         Tel:        +1 800 221-8025

         E-mail:     support@christiedigital.com"
    DESCRIPTION
        "The MIB module for CDS Entertainment Solutions CP2210 Cinema
         projector.
         iso(1).org(3).dod(6).internet(1).private(4).enterprises(1)
         .christiedigital(25766)
         .christieDigitalProduct(1)
         .cdEs(12).cdEsProjector(1)"
    REVISION      "201009141437Z" -- September 14, 2010
    DESCRIPTION
        "Added support for ICP Disk space"
    REVISION      "201008031933Z" -- August 03, 2010
    DESCRIPTION
        "Added: Icp1v2, Icp1v8, Icp2v5, Icp3v3,
         IcpCommunicating,LdCommunicating, LdLink0, LdLink1, LdLink2,
         LdLink3"
    REVISION      "201008031917Z" -- August 03, 2010
    DESCRIPTION
        "Added: LvpsACok, LvpsDCok,PowerGoodVid,
         PowerGood1v2and2v5,PowerGood1v8and3v3,
         PowerGood24vEXT,PowerGood24vSTBY"
    REVISION      "201008031915Z" -- August 03, 2010
    DESCRIPTION
        "Added: IcpType, DmdType, SatelliteTypes, IlsInstalled,TpcType,
         TpcOS,TpcDiskSpaceAvailable,TpcDiskSpaceUsed,
         TpcMemoryAvailable"
    REVISION      "201103301915Z" -- March 30, 2011
    DESCRIPTION
        "Updated: IcpType to include ICP 1.5 - 16 MegaByte Flash"
         
    ::= { cdEsProjector 4 }

-- ====================================================================
-- 
-- Lens Table - a table of lens entries

Cdcp2210LensIndex ::= TEXTUAL-CONVENTION
    STATUS        current
    DESCRIPTION
        "A value used to index the Lens table."
    SYNTAX        Integer32

-- ====================================================================
-- 
-- Versions - a table of serial numbers of install sw/hw components

Cdcp2210SerialNumberIdx ::= TEXTUAL-CONVENTION
    STATUS        current
    DESCRIPTION
        "A value used to index projector serial numbers."
    SYNTAX        Integer32 (1..64)

-- ====================================================================
-- 
-- Versions - a table of versions of install sw/hw components

Cdcp2210VersionsIdx ::= TEXTUAL-CONVENTION
    STATUS        current
    DESCRIPTION
        "A value used to index projector versions."
    SYNTAX        Integer32 (1..64)

-- ====================================================================
-- 
-- Admin only

X509Certificate ::= TEXTUAL-CONVENTION
    STATUS        current
    DESCRIPTION
        "An X509 digital certificate encoded as an ASN.1 DER object."
    SYNTAX        OCTET STRING (SIZE(0..4096))

cdcp2210Config OBJECT IDENTIFIER ::= { cp2210 1 }

cdcp2210VersionsTable OBJECT-TYPE
    SYNTAX        SEQUENCE OF Cdcp2210VersionsEntry
    MAX-ACCESS    not-accessible
    STATUS        current
    DESCRIPTION
        "A table listing the versions of the projectors hardware and
         software components."
    ::= { cdcp2210Config 1 }

cdcp2210VersionsEntry OBJECT-TYPE
    SYNTAX        Cdcp2210VersionsEntry
    MAX-ACCESS    not-accessible
    STATUS        current
    DESCRIPTION
        "The projector component description and version."
    INDEX
        { cdcp2210VersionsIndex }
    ::= { cdcp2210VersionsTable 1 }

Cdcp2210VersionsEntry ::= SEQUENCE
{
    cdcp2210VersionsIndex       Cdcp2210VersionsIdx,
    cdcp2210VersionsDescription DisplayString,
    cdcp2210VersionsVersion     DisplayString
}

cdcp2210VersionsIndex OBJECT-TYPE
    SYNTAX        Cdcp2210VersionsIdx
    MAX-ACCESS    read-only
    STATUS        current
    DESCRIPTION
        "Projector Configuration index to which the parameters in this
         row apply."
    ::= { cdcp2210VersionsEntry 1 }

cdcp2210VersionsDescription OBJECT-TYPE
    SYNTAX        DisplayString (SIZE(0..63))
    MAX-ACCESS    read-only
    STATUS        current
    DESCRIPTION
        "Component which this version entry maps to."
    ::= { cdcp2210VersionsEntry 2 }

cdcp2210VersionsVersion OBJECT-TYPE
    SYNTAX        DisplayString (SIZE(0..63))
    MAX-ACCESS    read-only
    STATUS        current
    DESCRIPTION
        "The version or serial number of the component this row
         represents.
         ."
    ::= { cdcp2210VersionsEntry 3 }

cdcp2210SerialNumberTable OBJECT-TYPE
    SYNTAX        SEQUENCE OF Cdcp2210SerialNumberEntry
    MAX-ACCESS    not-accessible
    STATUS        current
    DESCRIPTION
        "A table listing the serial numbers of the projectors hardware
         and software components."
    ::= { cdcp2210Config 2 }

cdcp2210SerialNumberEntry OBJECT-TYPE
    SYNTAX        Cdcp2210SerialNumberEntry
    MAX-ACCESS    not-accessible
    STATUS        current
    DESCRIPTION
        "The projector component description and serial number."
    INDEX
        { cdcp2210SerialNumberIndex }
    ::= { cdcp2210SerialNumberTable 1 }

Cdcp2210SerialNumberEntry ::= SEQUENCE
{
    cdcp2210SerialNumberIndex       Cdcp2210SerialNumberIdx,
    cdcp2210SerialNumberDescription DisplayString,
    cdcp2210SerialNumberVersion     DisplayString
}

cdcp2210SerialNumberIndex OBJECT-TYPE
    SYNTAX        Cdcp2210SerialNumberIdx
    MAX-ACCESS    read-only
    STATUS        current
    DESCRIPTION
        "Projector Configuration index to which the parameters in this
         row apply."
    ::= { cdcp2210SerialNumberEntry 1 }

cdcp2210SerialNumberDescription OBJECT-TYPE
    SYNTAX        DisplayString (SIZE(0..63))
    MAX-ACCESS    read-only
    STATUS        current
    DESCRIPTION
        "Component which this serial number entry maps to."
    ::= { cdcp2210SerialNumberEntry 2 }

cdcp2210SerialNumberVersion OBJECT-TYPE
    SYNTAX        DisplayString (SIZE(0..63))
    MAX-ACCESS    read-only
    STATUS        current
    DESCRIPTION
        "The serial number of the component this row represents. ."
    ::= { cdcp2210SerialNumberEntry 3 }

cdcp2210Priv OBJECT IDENTIFIER ::= { cdcp2210Config 3 }

cdcp2210CertificateIcp OBJECT-TYPE
    SYNTAX        X509Certificate
    MAX-ACCESS    read-only
    STATUS        current
    DESCRIPTION
        "This object contains the Interface Certificate.  The object
         value must be the ASN.1 DER encoding of the MTA manufacturer's
         X.509 public key certificate. ,contains the MTA's MAC  address.
         It The MTA Manufacturer Certificate is issued to each MTA
         manufacturer and is installed into each MTA at the time of
         manufacture or with a secure code download. The specific
         requirements related to this certificate are defined in  the
         Security specification."
    REFERENCE
        "Security Specification."
    ::= { cdcp2210Priv 1 }

cdcp2210CertificateLD OBJECT-TYPE
    SYNTAX        X509Certificate
    MAX-ACCESS    read-only
    STATUS        current
    DESCRIPTION
        "ASN.1 DER encoding of the MTA's X.509 public-key  certificate
         issued by the manufacturer and installed  into the embedded-MTA
         in the factory. This certificate,  called Certificate, cannot
         be updated by the provisioning server."
    ::= { cdcp2210Priv 2 }

cdcp2210IcpType OBJECT-TYPE
    SYNTAX        INTEGER {
        -- Unknown
        na(1),
        -- 8 MegaByte flash
        series2mb8(2),
        -- 16 MegaByte flash
        series2mb16(3),
        -- ICP 1.5 - 16 MegaByte flash
        series2Icp15mb16(4)

    }
    MAX-ACCESS    read-only
    STATUS        current
    DESCRIPTION
        "Returns the ICP type:
         Series2 - 8 MB flash 
         Series2 - 16 MB flash
         Series2 - ICP 1.5 - 16 MB flash"
    ::= { cdcp2210Config 4 }

cdcp2210DmdType OBJECT-TYPE
    SYNTAX        INTEGER {
        -- Not attached or unknown
        na(1),
        -- .98 inch DMD
        dc2k98(2),
        -- 2k 1.2 inch DMD
        dc2k12(3),
        -- 4k 1.38 inch DMD
        dc4k138(4)
    }
    MAX-ACCESS    read-only
    STATUS        current
    DESCRIPTION
        "Returns the DMD Type:
         2K - 0.98 inch DMD
         2K - 1.2 inch DMD
         4K - 1.38 inch DMD"
    ::= { cdcp2210Config 5 }

cdcp2210SatelliteType OBJECT IDENTIFIER ::= { cdcp2210Config 6 }

cdcp2210RedSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp2210SatelliteType 1 }

cdcp2210GreenSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp2210SatelliteType 2 }

cdcp2210BlueSatelliteType OBJECT-TYPE
    SYNTAX        INTEGER {
        -- Unknown or not attached
        na(1),
        -- DDR formatter
        ddr(2),
        -- LVDS Formatter
        lvds(3),
        -- DDR 4K formatter
        ddr4k(4)
    }
    MAX-ACCESS    read-only
    STATUS        current
    DESCRIPTION
        "Returns the Formatter type None/Unknown DDR LVDS DDR 4K"
    ::= { cdcp2210SatelliteType 3 }

cdcp2210Peripherals OBJECT IDENTIFIER ::= { cdcp2210Config 7 }

cdcp2210IlsInstalled OBJECT-TYPE
    SYNTAX        TruthValue
    MAX-ACCESS    read-only
    STATUS        current
    DESCRIPTION
        "Returns true if ILS is installed otherwise returns false."
    ::= { cdcp2210Peripherals 1 }

cdcp2210LdInstalled OBJECT-TYPE
    SYNTAX        TruthValue
    MAX-ACCESS    read-only
    STATUS        current
    DESCRIPTION
        "Returns true if LD is installed otherwise returns false."
    ::= { cdcp2210Peripherals 2 }

cdcp2210MediaBlockInstalled OBJECT-TYPE
    SYNTAX        TruthValue
    MAX-ACCESS    read-only
    STATUS        current
    DESCRIPTION
        "Returns true if MediaBlock is installed otherwise returns
         false."
    ::= { cdcp2210Peripherals 3 }

cdcp2210Status OBJECT IDENTIFIER ::= { cp2210 2 }

-- ====================================================================
-- 
-- Security status group

cdcp2210SecurityStatus OBJECT IDENTIFIER ::= { cdcp2210Status 1 }

cdcp2210SecurityArmed OBJECT-TYPE
    SYNTAX        INTEGER {
        armed(1),
        notArmed(2),
        na(3)
    }
    MAX-ACCESS    read-only
    STATUS        current
    DESCRIPTION
        "Security enclosure armed."
    ::= { cdcp2210SecurityStatus 1 }

cdcp2210SecurityTamper OBJECT-TYPE
    SYNTAX        INTEGER {
        tamper(1),
        secure(2),
        na(3)
    }
    MAX-ACCESS    read-only
    STATUS        current
    DESCRIPTION
        "Security enclosure tamper."
    ::= { cdcp2210SecurityStatus 2 }

cdcp2210MarriageActive OBJECT-TYPE
    SYNTAX        INTEGER {
        married(1),
        marriageBroken(2),
        na(3)
    }
    MAX-ACCESS    read-only
    STATUS        current
    DESCRIPTION
        "Marriage State,  When marriage is broken, no encrypted content
         can be played."
    ::= { cdcp2210SecurityStatus 3 }

cdcp2210PhysicalMarriageTamper OBJECT-TYPE
    SYNTAX        INTEGER {
        tampered(1),
        secure(2),
        na(3)
    }
    MAX-ACCESS    read-only
    STATUS        current
    DESCRIPTION
        "Physical Marriage State, Removal of any board within the card
         cage will cause a Physical tamper."
    ::= { cdcp2210SecurityStatus 4 }

cdcp2210LogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the LD board or Image Media Block."
    ::= { cdcp2210SecurityStatus 5 }

cdcp2210SoftwareCertZeroization OBJECT-TYPE
    SYNTAX        INTEGER {
        zeroed(1),
        ok(2),
        na(3)
    }
    MAX-ACCESS    read-only
    STATUS        current
    DESCRIPTION
        "Certificate State, A zeroed certificate state indicates  that
         a tamper has occurred on the LD board."
    ::= { cdcp2210SecurityStatus 6 }

cdcp2210ServiceDoorTamper OBJECT-TYPE
    SYNTAX        INTEGER {
        tamper(1),
        secure(2),
        na(3)
    }
    MAX-ACCESS    read-only
    STATUS        current
    DESCRIPTION
        "Service door to light engine compartment"
    ::= { cdcp2210SecurityStatus 7 }

cdcp2210TopEnclosureOpen OBJECT-TYPE
    SYNTAX        INTEGER {
        tamper(1),
        secure(2),
        na(3)
    }
    MAX-ACCESS    read-only
    STATUS        current
    DESCRIPTION
        "Security enclosure state, top side."
    ::= { cdcp2210SecurityStatus 8 }

cdcp2210BottomEnclosureOpen OBJECT-TYPE
    SYNTAX        INTEGER {
        tamper(1),
        secure(2),
        na(3)
    }
    MAX-ACCESS    read-only
    STATUS        current
    DESCRIPTION
        "Security enclosure state, top side."
    ::= { cdcp2210SecurityStatus 9 }

cdcp2210SecurityBatteryEvent OBJECT-TYPE
    SYNTAX        INTEGER {
        failed(1),
        ok(2),
        na(3)
    }
    MAX-ACCESS    read-only
    STATUS        current
    DESCRIPTION
        "Battery failed"
    ::= { cdcp2210SecurityStatus 10 }

cdcp2210BatteryLow OBJECT-TYPE
    SYNTAX        INTEGER {
        low(1),
        ok(2),
        na(3)
    }
    MAX-ACCESS    read-only
    STATUS        current
    DESCRIPTION
        "Battery state."
    ::= { cdcp2210SecurityStatus 11 }

cdcp2210SecurityLog OBJECT-TYPE
    SYNTAX        INTEGER {
        ok(1),
        warning(2),
        error(3),
        na(4)
    }
    MAX-ACCESS    read-only
    STATUS        current
    DESCRIPTION
        "The Security Log Warning indicates that there are  less than
         100 log entry locations available before  unread log entries
         will be overwritten.

         The Security Log Error indicates that there is no  more room to
         write log entries.

         When this warning/error is active, the Server needs  to extract
         the log data (via ASM/TLS session) from  the LD Security Log.
         Reads of the security log by any other entity/means will not
         impact this warning."
    ::= { cdcp2210SecurityStatus 12 }
    
cdcp2210IMBSecurityArmed OBJECT-TYPE
    SYNTAX        INTEGER {
        armed(1),
        notArmed(2),
        na(3)
    }
    MAX-ACCESS    read-only
    STATUS        current
    DESCRIPTION
        "IMB Security enclosure armed."
    ::= { cdcp2210SecurityStatus 13 }

cdcp2210IMBSecurityTamper OBJECT-TYPE
    SYNTAX        INTEGER {
        tamper(1),
        secure(2),
        na(3)
    }
    MAX-ACCESS    read-only
    STATUS        current
    DESCRIPTION
        "IMB Security enclosure tamper."
    ::= { cdcp2210SecurityStatus 14 }

cdcp2210IMBMarriageActive OBJECT-TYPE
    SYNTAX        INTEGER {
        married(1),
        marriageBroken(2),
        na(3)
    }
    MAX-ACCESS    read-only
    STATUS        current
    DESCRIPTION
        "IMB Marriage State,  When marriage is broken, no encrypted content
         can be played."
    ::= { cdcp2210SecurityStatus 15 }

cdcp2210IMBPhysicalMarriageTamper OBJECT-TYPE
    SYNTAX        INTEGER {
        tampered(1),
        secure(2),
        na(3)
    }
    MAX-ACCESS    read-only
    STATUS        current
    DESCRIPTION
        "IMB Physical Marriage State, Removal of any board within the card
         cage will cause a Physical tamper."
    ::= { cdcp2210SecurityStatus 16 }

cdcp2210IMBLogicalMarriageTamper OBJECT-TYPE
    SYNTAX        INTEGER {
        tampered(1),
        secure(2),
        na(3)
    }
    MAX-ACCESS    read-only
    STATUS        current
    DESCRIPTION
        "Local Marriage State, The cryptographic exchange which
         establishes/verifies a FIPS logical marriage with the ICP and
         the Image Media Block."
    ::= { cdcp2210SecurityStatus 17 }
    
cdcp2210IMBServiceDoorArmed OBJECT-TYPE
    SYNTAX        INTEGER {
        armed(1),
        tamper(2),
        na(3)
    }
    MAX-ACCESS    read-only
    STATUS        current
    DESCRIPTION
        "Service door to light engine compartment"
    ::= { cdcp2210SecurityStatus 18 }

cdcp2210IMBServiceDoorTamper OBJECT-TYPE
    SYNTAX        INTEGER {
        tamper(1),
        secure(2),
        na(3)
    }
    MAX-ACCESS    read-only
    STATUS        current
    DESCRIPTION
        "IMB Service door to light engine compartment"
    ::= { cdcp2210SecurityStatus 19 }

cdcp2210IMBBatteryLow OBJECT-TYPE
    SYNTAX        INTEGER {
        low(1),
        ok(2),
        na(3)
    }
    MAX-ACCESS    read-only
    STATUS        current
    DESCRIPTION
        "IMB Battery state."
    ::= { cdcp2210SecurityStatus 20 }
    
cdcp2210IMBICPCommunicationError OBJECT-TYPE
    SYNTAX        INTEGER {
        error(1),
        ok(2),
        na(3)
    }
    MAX-ACCESS    read-only
    STATUS        current
    DESCRIPTION
        "IMB Battery state."
    ::= { cdcp2210SecurityStatus 21 }

-- ====================================================================
-- 
-- Sensor tables

cdcp2210Sensors OBJECT IDENTIFIER ::= { cdcp2210Status 2 }

cdcp2210TempSensorsTable OBJECT-TYPE
    SYNTAX        SEQUENCE OF Cdcp2210TempSensorsEntry
    MAX-ACCESS    not-accessible
    STATUS        current
    DESCRIPTION
        "Table of temperature sensors and their values."
    ::= { cdcp2210Sensors 1 }

cdcp2210TempSensorsEntry OBJECT-TYPE
    SYNTAX        Cdcp2210TempSensorsEntry
    MAX-ACCESS    not-accessible
    STATUS        current
    DESCRIPTION
        "An entry containing a device and its statistics."
    INDEX
        { cdcp2210TempSensorsIndex }
    ::= { cdcp2210TempSensorsTable 1 }

Cdcp2210TempSensorsEntry ::= SEQUENCE
{
    cdcp2210TempSensorsIndex      Integer32,
    cdcp2210TempSensorsDevice     DisplayString,
    cdcp2210TempSensorsDiodeError TruthValue,
    cdcp2210TempSensorsLowerLimit TruthValue,
    cdcp2210TempSensorsUpperLimit TruthValue,
    cdcp2210TempSensorsValue      Gauge32
}

cdcp2210TempSensorsIndex OBJECT-TYPE
    SYNTAX        Integer32 (0..65535)
    MAX-ACCESS    read-only
    STATUS        current
    DESCRIPTION
        "Reference index for each observed device."
    ::= { cdcp2210TempSensorsEntry 1 }

cdcp2210TempSensorsDevice OBJECT-TYPE
    SYNTAX        DisplayString (SIZE(0..63))
    MAX-ACCESS    read-only
    STATUS        current
    DESCRIPTION
        "The name of the temperature sensor we are reading."
    ::= { cdcp2210TempSensorsEntry 2 }

cdcp2210TempSensorsDiodeError OBJECT-TYPE
    SYNTAX        TruthValue
    MAX-ACCESS    read-only
    STATUS        current
    DESCRIPTION
        "True if a diode error has occured."
    ::= { cdcp2210TempSensorsEntry 3 }

cdcp2210TempSensorsLowerLimit OBJECT-TYPE
    SYNTAX        TruthValue
    MAX-ACCESS    read-only
    STATUS        current
    DESCRIPTION
        "True if the sensor has breached it's lower limit."
    ::= { cdcp2210TempSensorsEntry 4 }

cdcp2210TempSensorsUpperLimit OBJECT-TYPE
    SYNTAX        TruthValue
    MAX-ACCESS    read-only
    STATUS        current
    DESCRIPTION
        "True if the sensor has breached it's upper limit."
    ::= { cdcp2210TempSensorsEntry 5 }

cdcp2210TempSensorsValue OBJECT-TYPE
    SYNTAX        Gauge32
    MAX-ACCESS    read-only
    STATUS        current
    DESCRIPTION
        "The temperature of this sensor in Celsius"
    ::= { cdcp2210TempSensorsEntry 6 }

cdcp2210FanSensorsTable OBJECT-TYPE
    SYNTAX        SEQUENCE OF Cdcp2210FanSensorsEntry
    MAX-ACCESS    not-accessible
    STATUS        current
    DESCRIPTION
        "Table of fan sensors and their values."
    ::= { cdcp2210Sensors 2 }

cdcp2210FanSensorsEntry OBJECT-TYPE
    SYNTAX        Cdcp2210FanSensorsEntry
    MAX-ACCESS    not-accessible
    STATUS        current
    DESCRIPTION
        "An entry containing a device and its statistics."
    INDEX
        { cdcp2210FanSensorsIndex }
    ::= { cdcp2210FanSensorsTable 1 }

Cdcp2210FanSensorsEntry ::= SEQUENCE
{
    cdcp2210FanSensorsIndex   Integer32,
    cdcp2210FanSensorsDevice  DisplayString,
    cdcp2210FanSensorsFault   TruthValue,
    cdcp2210FanSensorsTooSlow TruthValue,
    cdcp2210FanSensorsValue   Gauge32
}

cdcp2210FanSensorsIndex OBJECT-TYPE
    SYNTAX        Integer32 (0..65535)
    MAX-ACCESS    read-only
    STATUS        current
    DESCRIPTION
        "Reference index for each observed device."
    ::= { cdcp2210FanSensorsEntry 1 }

cdcp2210FanSensorsDevice OBJECT-TYPE
    SYNTAX        DisplayString (SIZE(0..63))
    MAX-ACCESS    read-only
    STATUS        current
    DESCRIPTION
        "The name of the fan sensor we are reading."
    ::= { cdcp2210FanSensorsEntry 2 }

cdcp2210FanSensorsFault OBJECT-TYPE
    SYNTAX        TruthValue
    MAX-ACCESS    read-only
    STATUS        current
    DESCRIPTION
        "True if the fan has faulted."
    ::= { cdcp2210FanSensorsEntry 3 }

cdcp2210FanSensorsTooSlow OBJECT-TYPE
    SYNTAX        TruthValue
    MAX-ACCESS    read-only
    STATUS        current
    DESCRIPTION
        "True if a fan speed error has occured with this fan."
    ::= { cdcp2210FanSensorsEntry 4 }

cdcp2210FanSensorsValue OBJECT-TYPE
    SYNTAX        Gauge32
    MAX-ACCESS    read-only
    STATUS        current
    DESCRIPTION
        "The rotation speed of the fan in RPM."
    ::= { cdcp2210FanSensorsEntry 5 }

cdcp2210InterlockSensorsTable OBJECT-TYPE
    SYNTAX        SEQUENCE OF Cdcp2210InterlockSensorsEntry
    MAX-ACCESS    not-accessible
    STATUS        current
    DESCRIPTION
        "Table of interlock sensors and their value."
    ::= { cdcp2210Sensors 3 }

cdcp2210InterlockSensorsEntry OBJECT-TYPE
    SYNTAX        Cdcp2210InterlockSensorsEntry
    MAX-ACCESS    not-accessible
    STATUS        current
    DESCRIPTION
        "An entry containing a device and its statistics."
    INDEX
        { cdcp2210InterlockSensorsIndex }
    ::= { cdcp2210InterlockSensorsTable 1 }

Cdcp2210InterlockSensorsEntry ::= SEQUENCE
{
    cdcp2210InterlockSensorsIndex  Integer32,
    cdcp2210InterlockSensorsDevice DisplayString,
    cdcp2210InterlockSensorsValue  INTEGER
}

cdcp2210InterlockSensorsIndex OBJECT-TYPE
    SYNTAX        Integer32 (0..65535)
    MAX-ACCESS    read-only
    STATUS        current
    DESCRIPTION
        "Reference index for each observed device."
    ::= { cdcp2210InterlockSensorsEntry 1 }

cdcp2210InterlockSensorsDevice OBJECT-TYPE
    SYNTAX        DisplayString (SIZE(0..63))
    MAX-ACCESS    read-only
    STATUS        current
    DESCRIPTION
        "The name of the interlock sensor we are reading."
    ::= { cdcp2210InterlockSensorsEntry 2 }

cdcp2210InterlockSensorsValue OBJECT-TYPE
    SYNTAX        INTEGER {
        open(1),
        closed(2),
        troubleOpen(3),
        troubleClosed(4)
    }
    MAX-ACCESS    read-only
    STATUS        current
    DESCRIPTION
        "The status of this interlock."
    ::= { cdcp2210InterlockSensorsEntry 3 }

-- ====================================================================
-- 
-- System health table, reports diagnostic test results.

cdcp2210SystemHealthTable OBJECT-TYPE
    SYNTAX        SEQUENCE OF Cdcp2210SystemHealthEntry
    MAX-ACCESS    not-accessible
    STATUS        current
    DESCRIPTION
        "Table of diagnostic tests and their results"
    ::= { cdcp2210Status 3 }

cdcp2210SystemHealthEntry OBJECT-TYPE
    SYNTAX        Cdcp2210SystemHealthEntry
    MAX-ACCESS    not-accessible
    STATUS        current
    DESCRIPTION
        "Each row respresents a diagnostic test and the result."
    INDEX
        { cdcp2210SystemHealthIndex }
    ::= { cdcp2210SystemHealthTable 1 }

Cdcp2210SystemHealthEntry ::= SEQUENCE
{
    cdcp2210SystemHealthIndex  Integer32,
    cdcp2210SystemHealthName   DisplayString,
    cdcp2210SystemHealthResult DisplayString
}

cdcp2210SystemHealthIndex OBJECT-TYPE
    SYNTAX        Integer32 (0..65535)
    MAX-ACCESS    read-only
    STATUS        current
    DESCRIPTION
        "Reference index for each observed test."
    ::= { cdcp2210SystemHealthEntry 1 }

cdcp2210SystemHealthName OBJECT-TYPE
    SYNTAX        DisplayString (SIZE(0..127))
    MAX-ACCESS    read-only
    STATUS        current
    DESCRIPTION
        "Name of the diagnostic being reported."
    ::= { cdcp2210SystemHealthEntry 2 }

cdcp2210SystemHealthResult OBJECT-TYPE
    SYNTAX        DisplayString (SIZE(0..127))
    MAX-ACCESS    read-only
    STATUS        current
    DESCRIPTION
        "Result of diagnostic."
    ::= { cdcp2210SystemHealthEntry 3 }

cdcp2210LensTable OBJECT-TYPE
    SYNTAX        SEQUENCE OF Cdcp2210LensEntry
    MAX-ACCESS    not-accessible
    STATUS        current
    DESCRIPTION
        "A table listing the lens entries."
    ::= { cdcp2210Status 4 }

cdcp2210LensEntry OBJECT-TYPE
    SYNTAX        Cdcp2210LensEntry
    MAX-ACCESS    not-accessible
    STATUS        current
    DESCRIPTION
        "The number of hours the projector has operated."
    INDEX
        { cdcp2210LensIdx }
    ::= { cdcp2210LensTable 1 }

Cdcp2210LensEntry ::= SEQUENCE
{
    cdcp2210LensIdx          Cdcp2210LensIndex,
    cdcp2210LensClass        DisplayString,
    cdcp2210LensType         DisplayString,
    cdcp2210LensSerialNumber DisplayString,
    cdcp2210LensStatus       INTEGER
}

cdcp2210LensIdx OBJECT-TYPE
    SYNTAX        Cdcp2210LensIndex (0..65535)
    MAX-ACCESS    read-only
    STATUS        current
    DESCRIPTION
        "Projector Lens index.  Each entry represents a various
         attributes of the Lens"
    ::= { cdcp2210LensEntry 1 }

cdcp2210LensClass OBJECT-TYPE
    SYNTAX        DisplayString (SIZE(0..255))
    MAX-ACCESS    read-only
    STATUS        current
    DESCRIPTION
        "Lens Class (Primary, Secondry...)"
    ::= { cdcp2210LensEntry 2 }

cdcp2210LensType OBJECT-TYPE
    SYNTAX        DisplayString (SIZE(0..255))
    MAX-ACCESS    read-only
    STATUS        current
    DESCRIPTION
        "Lens Type"
    ::= { cdcp2210LensEntry 3 }

cdcp2210LensSerialNumber OBJECT-TYPE
    SYNTAX        DisplayString (SIZE(0..255))
    MAX-ACCESS    read-only
    STATUS        current
    DESCRIPTION
        "Lens Serial Number"
    ::= { cdcp2210LensEntry 4 }

cdcp2210LensStatus OBJECT-TYPE
    SYNTAX        INTEGER {
        in(1),
        out(2)
    }
    MAX-ACCESS    read-only
    STATUS        current
    DESCRIPTION
        "Lens Status"
    ::= { cdcp2210LensEntry 5 }

cdcp2210System OBJECT IDENTIFIER ::= { cdcp2210Status 5 }

cdcp2210Tpc OBJECT IDENTIFIER ::= { cdcp2210System 1 }

cdcp2210TpcType OBJECT-TYPE
    SYNTAX        OCTET STRING
    MAX-ACCESS    read-only
    STATUS        current
    DESCRIPTION
        "Returns the TPC Type:
         TPC-660E TPC-650H"
    ::= { cdcp2210Tpc 1 }

cdcp2210TpcOs OBJECT-TYPE
    SYNTAX        OCTET STRING
    MAX-ACCESS    read-only
    STATUS        current
    DESCRIPTION
        "Returns the TPC OS Image"
    ::= { cdcp2210Tpc 2 }

cdcp2210TpcDiskSpaceAvailable OBJECT-TYPE
    SYNTAX        Integer32
    MAX-ACCESS    read-only
    STATUS        current
    DESCRIPTION
        "Returns the available TPC Disk Space"
    ::= { cdcp2210Tpc 3 }

cdcp2210TpcDiskSpaceUsed OBJECT-TYPE
    SYNTAX        Integer32
    MAX-ACCESS    read-only
    STATUS        current
    DESCRIPTION
        "Returns the TPC Disk Space, Used (MB)"
    ::= { cdcp2210Tpc 4 }

cdcp2210TpcMemorySpaceAvailable OBJECT-TYPE
    SYNTAX        Integer32
    MAX-ACCESS    read-only
    STATUS        current
    DESCRIPTION
        "Returns the available TPC Memory RAM (KB)"
    ::= { cdcp2210Tpc 5 }

cdcp2210Power OBJECT IDENTIFIER ::= { cdcp2210System 2 }

cdcp2210LvpsACok OBJECT-TYPE
    SYNTAX        INTEGER {
        -- OK
        yes(1),
        -- Fail
        no(2),
        -- Not available
        na(3)
    }
    MAX-ACCESS    read-only
    STATUS        current
    DESCRIPTION
        "Returns the AC OK signal state
         1 = yes
         2 = no
         3 = Not available"
    ::= { cdcp2210Power 1 }

cdcp2210LvpsDCok OBJECT-TYPE
    SYNTAX        INTEGER {
        -- OK
        yes(1),
        -- Fail
        no(2),
        -- Not available
        na(3)
    }
    MAX-ACCESS    read-only
    STATUS        current
    DESCRIPTION
        "Returns the CC OK signal state
         1 = yes
         2 = no
         3 = Not available"
    ::= { cdcp2210Power 2 }

cdcp2210PibPowerGoodVid OBJECT-TYPE
    SYNTAX        INTEGER {
        -- OK
        yes(1),
        -- Fail
        no(2),
        -- Not available
        na(3)
    }
    MAX-ACCESS    read-only
    STATUS        current
    DESCRIPTION
        "Returns the Power Good Vid signal state
         1 = yes
         2 = no
         3 = Not available"
    ::= { cdcp2210Power 3 }

cdcp2210PibPowerGood1v2and2v5 OBJECT-TYPE
    SYNTAX        INTEGER {
        -- OK
        yes(1),
        -- Fail
        no(2),
        -- Not available
        na(3)
    }
    MAX-ACCESS    read-only
    STATUS        current
    DESCRIPTION
        "Returns the PIB PowerGood signal for the 1.2v and 2.5v rails 1
         = yes
         2 = no
         3 = Not available"
    ::= { cdcp2210Power 4 }

cdcp2210PibPowerGood1v8and3v3 OBJECT-TYPE
    SYNTAX        INTEGER {
        -- OK
        yes(1),
        -- Fail
        no(2),
        -- Not available
        na(3)
    }
    MAX-ACCESS    read-only
    STATUS        current
    DESCRIPTION
        "Returns the PIB PowerGood signal for the 1.8v and 3.3v rails 1
         = yes
         2 = no
         3 = Not available"
    ::= { cdcp2210Power 5 }

cdcp2210PibPowerGood24vEXT OBJECT-TYPE
    SYNTAX        INTEGER {
        -- OK
        yes(1),
        -- Fail
        no(2),
        -- Not available
        na(3)
    }
    MAX-ACCESS    read-only
    STATUS        current
    DESCRIPTION
        "Returns the PIB PowerGood signal for the 24v External 1 = yes
         2 = no
         3 = Not available"
    ::= { cdcp2210Power 6 }

cdcp2210PibPowerGood24vSTBY OBJECT-TYPE
    SYNTAX        INTEGER {
        -- OK
        yes(1),
        -- Fail
        no(2),
        -- Not available
        na(3)
    }
    MAX-ACCESS    read-only
    STATUS        current
    DESCRIPTION
        "Returns the PIB PowerGood signal for the 24v Standby. 1 = yes
         2 = no
         3 = Not available"
    ::= { cdcp2210Power 7 }

cdcp2210Icp1v2 OBJECT-TYPE
    SYNTAX        OCTET STRING (SIZE(1..10))
    MAX-ACCESS    read-only
    STATUS        current
    DESCRIPTION
        "Returns the ICP 1.2v rail measurements or NA if in Standby"
    ::= { cdcp2210Power 8 }

cdcp2210Icp1v8 OBJECT-TYPE
    SYNTAX        OCTET STRING (SIZE(1..10))
    MAX-ACCESS    read-only
    STATUS        current
    DESCRIPTION
        "Returns the ICP 1.8v rail measurements or NA if in Standby"
    ::= { cdcp2210Power 9 }

cdcp2210Icp2v5 OBJECT-TYPE
    SYNTAX        OCTET STRING (SIZE(1..10))
    MAX-ACCESS    read-only
    STATUS        current
    DESCRIPTION
        "Returns the ICP 2.5v rail measurements or NA if in Standby"
    ::= { cdcp2210Power 10 }

cdcp2210Icp3v3 OBJECT-TYPE
    SYNTAX        OCTET STRING (SIZE(1..10))
    MAX-ACCESS    read-only
    STATUS        current
    DESCRIPTION
        "Returns the ICP 3.3v rail measurements or NA if in Standby"
    ::= { cdcp2210Power 11 }

cdcp2210IcpCommunicating OBJECT-TYPE
    SYNTAX        TruthValue
    MAX-ACCESS    read-only
    STATUS        current
    DESCRIPTION
        "Returns IPC State:
         True = Communicating False = Not Communicating"
    ::= { cdcp2210System 3 }

cdcp2210LinkDecryptor OBJECT IDENTIFIER ::= { cdcp2210System 4 }

cdcp2210LdCommunicating OBJECT-TYPE
    SYNTAX        TruthValue
    MAX-ACCESS    read-only
    STATUS        current
    DESCRIPTION
        "Returns the ICP connection state. True = Communicating False =
         Not Communicating"
    ::= { cdcp2210LinkDecryptor 1 }

cdcp2210LdLink0 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link states:
         No Source Decryption Not Active Decryption Active Decryption
         Error Unknown"
    ::= { cdcp2210LinkDecryptor 2 }

cdcp2210LdLink1 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link1 states:
         No Source Decryption Not Active Decryption Active Decryption
         Error Unknown"
    ::= { cdcp2210LinkDecryptor 3 }

cdcp2210LdLink2 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link2 states:
         No Source Decryption Not Active Decryption Active Decryption
         Error Unknown"
    ::= { cdcp2210LinkDecryptor 4 }

cdcp2210LdLink3 OBJECT-TYPE
    SYNTAX        INTEGER {
        -- No source
        noSource(1),
        -- Decryption Not Actice
        decryptionNotActive(2),
        -- Decryption Active
        decryptionActive(3),
        -- Decryption Error
        decryptionError(4),
        -- Unknown
        unknown(5)
    }
    MAX-ACCESS    read-only
    STATUS        current
    DESCRIPTION
        "Returns the LD Link3 states:
         No Source Decryption Not Active Decryption Active Decryption
         Error Unknown"
    ::= { cdcp2210LinkDecryptor 5 }

cdcp2210Icp OBJECT-IDENTITY
    STATUS        current
    DESCRIPTION
        "ICP related objects"
    ::= { cdcp2210System 5 }

cdcp2210IcpDiskSpaceTotal OBJECT-TYPE
    SYNTAX        Integer32
    MAX-ACCESS    read-only
    STATUS        current
    DESCRIPTION
        "Returns the available ICP Disk Space (KB)"
    ::= { cdcp2210Icp 1 }

cdcp2210IcpDiskSpaceFree OBJECT-TYPE
    SYNTAX        Integer32
    MAX-ACCESS    read-only
    STATUS        current
    DESCRIPTION
        "Returns the ICP Disk Space, Free (KB)"
    ::= { cdcp2210Icp 2 }

cdcp2210StatusPeripherals OBJECT IDENTIFIER ::= { cdcp2210Status 6 }

END
