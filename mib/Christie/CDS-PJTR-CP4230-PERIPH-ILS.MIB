CDS-PJTR-CP4230-PERIPH-ILS DEFINITIONS ::= BEGIN

IMPORTS
    cdcp4230StatusPeripherals
        FROM CDS-PJTR-CP4230
    MODULE-COMPLIANCE, NOTIFICATION-GROUP, OBJECT-GROUP
        FROM SNMPv2-CONF
    MODULE-IDENTITY, NOTIFICATION-TYPE, OBJECT-IDENTITY, OBJECT-TYPE
        FROM SNMPv2-SMI
    TEXTUAL-CONVENTION
        FROM SNMPv2-TC
    ;

cdcp4230PeriphIls MODULE-IDENTITY
    LAST-UPDATED  "201008111814Z" -- August 11, 2010
    ORGANIZATION
        "Christie Digital Systems, Inc."
    CONTACT-INFO
        "Christie Digital Systems
         Customer Service

         Postal:     10550 Camden Drive
         Cypress, Ca 90630
         USA

         Tel:        +1 800 221-8025

         E-mail:     support@christiedigital.com"
    DESCRIPTION
        "The MIB module for CDS Entertainment Solutions CP4230 Cinema
         projector.
         iso(1).org(3).dod(6).internet(1).private(4).enterprises(1)
         .christiedigital(25766)
         .christieDigitalProduct(1)
         .cdEs(12).cdEsProjector(6)"
    ::= { cdcp4230StatusPeripherals 1 }

cdcp4230PeriphIlsNotifications OBJECT IDENTIFIER ::= { cdcp4230StatusPeripherals 0 }

cdcp4230PeriphIlsObjects OBJECT IDENTIFIER ::= { cdcp4230PeriphIls 1 }

cdcp4230PeriphIlsStats OBJECT IDENTIFIER ::= { cdcp4230PeriphIlsObjects 1 }

cdcp4230PeriphIlsCommunicating OBJECT-TYPE
    SYNTAX        INTEGER {
        yes(1),
        no(2),
        na(3)
    }
    MAX-ACCESS    read-only
    STATUS        current
    DESCRIPTION
        "Returns:
         yes, if ILS board is communicating no, if ILS board is
         communicating na, if board not installed"
    ::= { cdcp4230PeriphIlsStats 1 }

cdcp4230PeriphIlsBoardID OBJECT-TYPE
    SYNTAX        OCTET STRING (SIZE(0..20))
    MAX-ACCESS    read-only
    STATUS        current
    DESCRIPTION
        "Returns the Electronic board ID"
    ::= { cdcp4230PeriphIlsStats 2 }

cdcp4230PeriphIlsVersions OBJECT IDENTIFIER ::= { cdcp4230PeriphIlsStats 3 }

cdcp4230PeriphIlsBootVersion OBJECT-TYPE
    SYNTAX        OCTET STRING (SIZE(0..20))
    MAX-ACCESS    read-only
    STATUS        current
    DESCRIPTION
        "Returns the Boot Loader version"
    ::= { cdcp4230PeriphIlsVersions 1 }

cdcp4230PeriphIlsMainVersion OBJECT-TYPE
    SYNTAX        OCTET STRING (SIZE(0..20))
    MAX-ACCESS    read-only
    STATUS        current
    DESCRIPTION
        "Returns the Main Software version"
    ::= { cdcp4230PeriphIlsVersions 2 }

cdcp4230PeriphIlsHwVersion OBJECT-TYPE
    SYNTAX        OCTET STRING (SIZE(0..20))
    MAX-ACCESS    read-only
    STATUS        current
    DESCRIPTION
        "Returns the Hardware version"
    ::= { cdcp4230PeriphIlsVersions 3 }

cdcp4230PeriphIlsTemperature OBJECT-TYPE
    SYNTAX        INTEGER (-999..200)
    MAX-ACCESS    read-only
    STATUS        current
    DESCRIPTION
        "Returns the onboard temperature (or -999 if not avaliable)"
    ::= { cdcp4230PeriphIlsStats 4 }

cdcp4230PeriphIlsMainCrcOK OBJECT-TYPE
    SYNTAX        INTEGER {
        yes(1),
        no(2),
        na(3)
    }
    MAX-ACCESS    read-only
    STATUS        current
    DESCRIPTION
        "Returns:
         yes, if Main software CRC is OK. no, if Main software CRC is
         not OK. na, if board not installed or not communicating"
    ::= { cdcp4230PeriphIlsStats 5 }

cdcp4230PeriphIlsSensors OBJECT IDENTIFIER ::= { cdcp4230PeriphIlsStats 6 }

cdcp4230PeriphIlsXSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp4230PeriphIlsSensors 1 }

cdcp4230PeriphIlsYSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp4230PeriphIlsSensors 2 }

cdcp4230PeriphIlsZoomSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp4230PeriphIlsSensors 3 }

cdcp4230PeriphIlsFocusSensorOK OBJECT-TYPE
    SYNTAX        INTEGER {
        yes(1),
        no(2),
        na(3)
    }
    MAX-ACCESS    read-only
    STATUS        current
    DESCRIPTION
        "Returns:
         yes, if Sensor is OK. no, if Sensor is not OK. na, if board not
         installed or not communicating"
    ::= { cdcp4230PeriphIlsSensors 4 }

cdcp4230PeriphIlsConfig OBJECT IDENTIFIER ::= { cdcp4230PeriphIlsObjects 3 }

cdcp4230PeriphIlsAutoEnabled OBJECT-TYPE
    SYNTAX        INTEGER {
        yes(1),
        no(2),
        na(3)
    }
    MAX-ACCESS    read-only
    STATUS        current
    DESCRIPTION
        "Returns 'Auto ILS' is enable state."
    ::= { cdcp4230PeriphIlsConfig 1 }

cdcp4230PeriphIlsResetOnStartup OBJECT-TYPE
    SYNTAX        INTEGER {
        yes(1),
        no(2),
        na(3)
    }
    MAX-ACCESS    read-only
    STATUS        current
    DESCRIPTION
        "Returns ILS 'Reset on Startup' state."
    ::= { cdcp4230PeriphIlsConfig 2 }

cdcp4230PeriphIlsResetOnBrownOut OBJECT-TYPE
    SYNTAX        INTEGER {
        yes(1),
        no(2),
        na(3)
    }
    MAX-ACCESS    read-only
    STATUS        current
    DESCRIPTION
        "Returns ILS 'Reset on Brown Out' state."
    ::= { cdcp4230PeriphIlsConfig 3 }

cdcp4230PeriphIlsConformance OBJECT IDENTIFIER ::= { cdcp4230PeriphIls 2 }

cdcp4230PeriphIlsCompliances OBJECT IDENTIFIER ::= { cdcp4230PeriphIlsConformance 1 }

cdcp4230PeriphIlsGroups OBJECT IDENTIFIER ::= { cdcp4230PeriphIlsConformance 2 }

cdcp4230PeriphIlsGroupAll OBJECT-GROUP
    OBJECTS
        { cdcp4230PeriphIlsBoardID, cdcp4230PeriphIlsCommunicating,
        cdcp4230PeriphIlsBootVersion, cdcp4230PeriphIlsMainVersion,
        cdcp4230PeriphIlsHwVersion, cdcp4230PeriphIlsTemperature,
        cdcp4230PeriphIlsMainCrcOK, cdcp4230PeriphIlsXSensorOK,
        cdcp4230PeriphIlsYSensorOK, cdcp4230PeriphIlsZoomSensorOK,
        cdcp4230PeriphIlsFocusSensorOK, cdcp4230PeriphIlsAutoEnabled,
        cdcp4230PeriphIlsResetOnStartup, cdcp4230PeriphIlsConfig }
    STATUS        current
    DESCRIPTION
        "Group of objects implemented in the projector peripherals (ILS
         option) for reporting the status of ILS."
    ::= { cdcp4230PeriphIlsGroups 1 }

END
